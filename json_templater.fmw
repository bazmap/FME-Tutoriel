FME workspace json_templater.fmw

Note: Création d'un champ JSON contenant les relations topologiques
JSONTemplater_2
    RESULT_ATTRIBUTE = topologie_detail
    ROOT_QUERY_EXPR:
      [
      	for $object_id at $pos in fme:get-list-attribute("topologie{}.id_relation")

      		let $id_relation := fme:get-attribute(concat("topologie{",$pos - 1,"}.id_relation"))

      		let $topologie_type := fme:get-attribute(concat("topologie{",$pos - 1,"}.topologie_type"))
      		let $topologie_sous_type := fme:get-attribute(concat("topologie{",$pos - 1,"}.topologie_sous_type"))

      		let $object_id := fme:get-attribute(concat("topologie{",$pos - 1,"}.object_id"))
      		let $object_type := fme:get-attribute(concat("topologie{",$pos - 1,"}.object_type"))
      		let $vertex_number := fme:get-attribute(concat("topologie{",$pos - 1,"}.vertex_number"))
      		let $vertex_position := fme:get-attribute(concat("topologie{",$pos - 1,"}.vertex_position"))

      		let $relation_object_id := fme:get-attribute(concat("topologie{",$pos - 1,"}.relation_object_id"))
      		let $relation_object_type := fme:get-attribute(concat("topologie{",$pos - 1,"}.relation_object_type"))
      		let $relation_vertex_number := fme:get-attribute(concat("topologie{",$pos - 1,"}.relation_vertex_number"))
      		let $relation_vertex_position := fme:get-attribute(concat("topologie{",$pos - 1,"}.relation_vertex_position"))

      		let $distance := fme:get-attribute(concat("topologie{",$pos - 1,"}.distance"))
      		let $angle := fme:get-attribute(concat("topologie{",$pos - 1,"}.angle"))

      		return {
      			"id_relation":$id_relation,

      			"topologie_type":$topologie_type,
      			"topologie_sous_type":$topologie_sous_type,

      			"object_id":$object_id,
      			"object_type":$object_type,
      			"vertex_number":$vertex_number,
      			"vertex_position":$vertex_position,

      			"relation_object_id":$relation_object_id,
      			"relation_object_type":$relation_object_type,
      			"relation_vertex_number":$relation_vertex_number,
      			"relation_vertex_position":$relation_vertex_position,

      			"distance":$distance,
      			"angle":$angle
      		}
      ]
    VISIBLE_QUERY_VALIDATE = Yes

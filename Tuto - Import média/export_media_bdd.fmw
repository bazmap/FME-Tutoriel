FME workspace export_media_bdd.fmw

Parameters:
- param_source = $(FME_MF_DIR)media_db.sqlite   # SQLite Database
- param_dest = $(FME_MF_DIR)media_export   # Emplacement des fichiers finaux

Readers:
- SQLITE3_1: SQLITE3 from $(param_source)

Writers:
- DATAFILE_1: DATAFILE to $(param_dest)

media_data (reader SQLITE3_1)
    attributes: miniature varchar(200), type_media varchar(200), chemin text, titre text, nom_media text, extension varchar(200), taille text, date_maj text, date_creation text, media_binaire text
    -> AttributeManager
Note: Nettoyage attributs
AttributeManager
    ATTR_TABLE:
      REMOVE miniature
      REMOVE chemin
      REMOVE titre
      REMOVE taille
      REMOVE date_maj
      REMOVE date_creation
    -> BinaryDecoder
Note: Décodage des données binaire en hexadecimal very le format binaire fme
BinaryDecoder
    ATTR_ENCODING = fme-binary
    ATTR_TABLE = media_binaire data_file_data
    ENCODING_TYPE = HEX
    -> File1 (writer DATAFILE_1)
File1 (writer DATAFILE_1)

FME workspace Export_media_GEO.fmw

Parameters:
- bdd_source = 1 - Local - 11 - Integration   # BDD source
- file_destination = C:\Users\abazin\Downloads   # Destination des fichiers
- jpeg_compression_level = 90   # Niveau de compression JPEG (0 - 100)

Readers:
- POSTGRES_1: POSTGRES from $(bdd_source)

Writers:
- JPEG_1: JPEG to $(file_destination)
- PNGRASTER_1: PNGRASTER to $(file_destination)

media (reader POSTGRES_1)
    attributes: id varchar(80),Unique, media_text varchar(80), media_bytea bytea, media_origine varchar(80), miniature bytea, nom_fichier varchar(80), type_media varchar(80), auteur varchar(80), date_ajout timestamp, commentaire varchar(80), id_objet varchar(80),BTREE, vitrine bool, num_desordre varchar(80),BTREE
    -> AttributeManager
Note: Nettoyage attributs
AttributeManager
    ATTR_TABLE:
      REMOVE id
      REMOVE media_text
      REMOVE media_origine
      REMOVE miniature
      REMOVE auteur
      REMOVE date_ajout
      REMOVE commentaire
      REMOVE id_objet
      REMOVE vitrine
      REMOVE num_desordre
    -> RasterReplacer
Note: Création image
RasterReplacer
    BLOB_ATTR = media_bytea
    FORMAT = FME_CONDITIONAL:DEFAULT_VALUE'JPEG2000'BOOL_OP;OR;COMPOSITE_TEST;1;TEST @Value(type_media) = image/jpeg'JPEG'BOOL_OP;OR;COMPOSITE_TEST;1;TEST @Value(type_media) = image/png'PNGRASTER'BOOL_OP;OR;COMPOSITE_TEST;1;TEST @Value(type_media) = image/tif'TIFF'BOOL_OP;OR;COMPOSITE_TEST;1;TEST @Value(type_media) = image/gif'GIFRASTER'BOOL_OP;OR;COMPOSITE_TEST;1;TEST @Value(type_media) = image/ecw'ECW'BOOL_OP;OR;COMPOSITE_TEST;1;TEST @Value(type_media) = image/geotif'GEOTIFF'FME_NUM_CONDITIONS7___
    REMOVE_ATTRIBUTE = Yes
    -> TestFilter
Note: Filtrage selon type
TestFilter
    DEFAULT_VALUE = Autres
    PASSED_TEST_GROUP_OUTPUT = FIRST
    TEST_LIST = "BOOL_OP,OR,COMPOSITE_TEST,""""""1"""""",TEST_CLAUSE,TEST @Value(type_media) = image/jpeg",JPEG,"BOOL_OP,OR,COMPOSITE_TEST,""""""1"""""",TEST_CLAUSE,TEST @Value(type_media) = image/png",PNG
    JPEG -> smart_intervention_task_oa.media (writer JPEG_1)
    PNG -> Raster1 (writer PNGRASTER_1)
smart_intervention_task_oa.media (writer JPEG_1)
Raster1 (writer PNGRASTER_1)

FME workspace import_media_GEO.fmw

Parameters:
- param_size_max_img = 500   # Taille maximum de la miniature en pixel (entre 10 et 1000 px) 
- param_img_to_min = img_to_min   # Utilisation de logos standards,logo_to_min%Miniaturisation des images,img_to_min Source des miniatures pour les images 
- param_source = C:\Users\abazin\Downloads\test   # Emplacement des fichiers 

Readers:
- PATH_1: PATH from $(param_source)

PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> AttributeManager
Note: Nettoyage des attributs
AttributeManager
    ATTR_TABLE:
      REMOVE path_unix
      RENAME_SET_VALUE path_windows > chemin
      RENAME_SET_VALUE path_rootname > titre
      RENAME_SET_VALUE path_filename > nom_media
      SET_TO extension = @LowerCase(@Value(path_extension))
      REMOVE path_extension
      RENAME_SET_VALUE path_filesize > taille
      REMOVE path_ownername
      REMOVE path_readonly
      RENAME_SET_VALUE path_modified_date > date_maj
      RENAME_SET_VALUE path_created_date > date_creation
      REMOVE path_accessed_date
      REMOVE path_directory_unix
      REMOVE path_directory_windows
      REMOVE path_type
      REMOVE fme_feature_type
    -> AttributeFileReader
Note: Récupération des médias
AttributeFileReader
    CHAR_ENCODING = fme-binary
    DEST_ATTR = media_binaire
    FILE_NAME = @Value(chemin)
    -> AttributeCreator
Note: Ajout d'attributs : / - miniature en base 64 / - type mime
AttributeCreator
    ATTR_TABLE:
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      SET_TO type_media = FME_CONDITIONAL:DEFAULT_VALUE'none'BOOL_OP;OR;COMPOSITE_TEST;1 OR 2;TEST @Value(extension) = jpg;TEST @Value(extension) = jpeg'image/jpeg'BOOL_OP;OR;COMPOSITE_TEST;1;TEST @Value(extension) = png'image/png'BOOL_OP;OR;COMPOSITE_TEST;1;TEST @Value(extension) = gif'image/gif'BOOL_OP;OR;COMPOSITE_TEST;1 OR 2;TEST @Value(extension) = tif;TEST @Value(extension) = tiff'image/tif'BOOL_OP;OR;COMPOSITE_TEST;1;TEST @Value(extension) = pdf'application/pdf'BOOL_OP;OR;COMPOSITE_TEST;1 OR 2;TEST @Value(extension) = doc;TEST @Value(extension) = docx'application/vnd.ms-word'BOOL_OP;OR;COMPOSITE_TEST;1 OR 2;TEST @Value(extension) = xls;TEST @Value(extension) = xlsx'application/vnd.ms-excel'BOOL_OP;OR;COMPOSITE_TEST;1 OR 2;TEST @Value(extension) = ppt;TEST @Value(extension) = pptx'application/vnd.ms-power-point'BOOL_OP;OR;COMPOSITE_TEST;1 OR 2;TEST @Value(extension) = htm;TEST @Value(extension) = html'text/html'FME_NUM_CONDITIONS10___
    -> TestFilter
Note: Filtrage selon le type de fichier
TestFilter
    DEFAULT_VALUE = document
    TEST_LIST:
      "BOOL_OP,COMPOSITE,COMPOSITE_TEST,""""""1 AND ( 2 OR 3 OR 4 )"""""",TEST_CLAUSE,TEST $(param_img_to_min) = img_to_min
      CASE_INSENSITIVE_TEST @Value(type_media) = image/jpeg
      CASE_INSENSITIVE_TEST @Value(type_media) = image/tif
      CASE_INSENSITIVE_TEST @Value(type_media) = image/gif",image
    image -> RasterReplacer
    document -> BinaryDecoder
Note: Création d'un raster à partir du média sous forme binaire
RasterReplacer
    BLOB_ATTR = media_binaire
    FORMAT = FME_CONDITIONAL:DEFAULT_VALUE'JPEG2000'BOOL_OP;OR;COMPOSITE_TEST;1;TEST @Value(type_media) = image/jpeg'JPEG'BOOL_OP;OR;COMPOSITE_TEST;1;TEST @Value(type_media) = image/png'PNGRASTER'BOOL_OP;OR;COMPOSITE_TEST;1;TEST @Value(type_media) = image/tif'TIFF'BOOL_OP;OR;COMPOSITE_TEST;1;TEST @Value(type_media) = image/gif'GIFRASTER'BOOL_OP;OR;COMPOSITE_TEST;1;TEST @Value(type_media) = image/ecw'ECW'BOOL_OP;OR;COMPOSITE_TEST;1;TEST @Value(type_media) = image/geotif'GEOTIFF'FME_NUM_CONDITIONS7___
    REMOVE_ATTRIBUTE = No
    -> RasterPropertyExtractor
Note: Récuépration des informations sur le raster (taille notamment)
RasterPropertyExtractor
    -> TestFilter_2
Note: Selon la taille, on redimentionne ou pas
TestFilter_2
    DEFAULT_VALUE = keep_original
    TEST_LIST:
      "BOOL_OP,OR,COMPOSITE_TEST,""""""1 OR 2"""""",TEST_CLAUSE,TEST @Value(_num_rows) >= $(param_size_max_img)
      TEST @Value(_num_columns) >= $(param_size_max_img)",resize
    resize -> AttributeCreator_2
    keep_original -> AttributeManager_2
Note: Calcul du ratio de redimensionnement
AttributeCreator_2
    ATTR_TABLE:
      SET_TO ratio_x = FME_CONDITIONAL:DEFAULT_VALUE'@Evaluate(@Value(_num_columns) * $(param_size_max_img) / @Value(_num_rows))'BOOL_OP;OR;COMPOSITE_TEST;1;TEST @Value(_num_columns) > @Value(_num_rows)'$(param_size_max_img)'FME_NUM_CONDITIONS2___
      SET_TO ratio_y = FME_CONDITIONAL:DEFAULT_VALUE'@Evaluate(@Value(_num_rows) * $(param_size_max_img) / @Value(_num_columns))'BOOL_OP;OR;COMPOSITE_TEST;1;TEST @Value(_num_rows) > @Value(_num_columns)'$(param_size_max_img)'FME_NUM_CONDITIONS2___
    -> RasterResampler
Note: Redimensionnement
RasterResampler
    COLUMNS = @Value(ratio_x)
    INTERPOLATION_TYPE_NAME = Bicubic
    ROWCOL_OR_CELLSIZE = RowsColumns
    ROWS = @Value(ratio_y)
    RESAMPLED -> RasterExtractor
Note: Récupération du raster au format binaire en miniature
RasterExtractor
    RASTER_BLOB_ATTR = miniature
    RASTER_FORMAT = JPEG
    RASTER_FORMAT_ATTR = format_miniature
    -> GeometryRemover
Note: Récupération de l'image original en tant que miniature
AttributeManager_2
    ATTR_TABLE = SET_TO miniature = @Value(media_binaire)
    -> GeometryRemover
Note: Suppression du raster
GeometryRemover
    -> AttributeRemover
Note: Encodage de la miniature de base64 vers binaire
BinaryDecoder
    ATTRS_TO_DECODE = miniature
    ATTR_ENCODING = fme-binary
    ENCODING_TYPE = Base64
    WRITE_TO_OTHER_ATTRS = No
    -> AttributeRemover
Note: Conservation des attributs GEO
AttributeRemover
    REMOVE_ATTRS = ratio_x,_rotation_x,_upper_right_x,_lower_left_y,_num_rows,_upper_right_y,format_miniature,_min_y,_lower_left_x,_lower_right_x,_num_bands,_min_x,_upper_left_x,_cell_origin_x,_rotation_y,_num_columns,_upper_left_y,_max_y,ratio_y,_max_x,_origin_x,_lower_right_y,_spacing_y,_origin_y,_spacing_x,_cell_origin_y

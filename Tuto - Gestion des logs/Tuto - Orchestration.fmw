FME workspace Tuto - Orchestration.fmw
Title: Tuto - Orchestration
Description: Le but de ce workspace est de lancer un second workspace ("Tuto - traitement.fmw") puis d'en récupérer le log afin de les analyser.

Note: Le but de ce workspace est de lancer un second workspace ("Tuto - traitement.fmw") puis d'en récupérer le log afin de les analyser.
Note: Initialisation
Creator
    GEOMTYPE = Geometry Object
    NUM = 1
    CREATED -> WorkspaceRunner
Note: Lancement du workspace
WorkspaceRunner
    BLOCKING = Yes
    WORKSPACE_FILE = $(FME_MF_DIR_USERTYPED)\Tuto - traitement.fmw
    SUCCEEDED -> logAnalysator [FeatureReader_Initiator]
    FAILED -> logAnalysator [FeatureReader_Initiator]
Note: Utilisation d'un transformer personnalisé pour épurer le script
logAnalysator
    file = $(FME_MF_DIR_USERTYPED)\Tuto - Traitement.log
    html_repport = YES

FME custom transformer logAnalysator

Parameters:
- file = $(FME_MF_DIR)Tuto - Traitement.log   # Fichier log du traitement
- html_repport = YES   # Générer un rapport HTML

Note: Le but de ce transformer personnalisé est de récupérer les logs d'un workspace puis de les parser afin de pouvoir en extraire un rapport HTML.
Note: Entrée du transformer personnalisé
FeatureReader_Initiator (input)
    -> FeatureReader [INITIATOR]
Note: Lecture du fichier log issu du workspace / Utilisation d'un reader CSV : le log est formaté comme un CSV dont le séparateur serait "|".
FeatureReader
    ATTRIBUTES = CSV,"col0,col1,col2,col3,col4"
    ATTR_ACCUM_MODE = Only Use Result
    COMBINE_GEOM = Use Result
    CSV2_CASE_SENSITIVE_FIELD_NAMES = Yes
    CSV2_CHUNK_SIZE = 100000
    CSV2_DATA_START_LINE = 1
    CSV2_DATE_INPUT_FORMAT = ISO
    CSV2_DELIMITER = auto
    CSV2_DELIMITER_DETECTION_ALGORITHM = EQUAL_FIELDS_PER_LINE
    CSV2_ENCODING = utf-8
    CSV2_ENFORCE_STRICT_SCHEMA = No
    CSV2_FEATURE_TYPE_NAME = FORMAT_NAME
    CSV2_FIELD_NAMES_LINE = 0
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 250000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = $(file)
    FORMAT = CSV2
    INTERACT = NONE
    ORDER_RESULTS = No
    OUTPUT_ADD_SCHEMA_ATTRIBUTES = NO
    OUTPUT_FEATURES_DISPLAY = Schema and Data Features
    CSV -> AttributeManager
Note: Renommage colonnes
AttributeManager
    ATTR_TABLE:
      RENAME_SET_VALUE col0 > timestamp (datetime)
      RENAME_SET_VALUE col1 > cpu_time (real32)
      RENAME_SET_VALUE col2 > total_time (real32)
      RENAME_SET_VALUE col3 > level (varchar(6))
      RENAME_SET_VALUE col4 > message (varchar(261))
    -> AttributeFilter
Note: Filtre selon le niveau de sévérité du message
AttributeFilter
    ATTR_NAME = level
    ATTR_VALUES = <Empty>,<Missing>,<Null>,<Unfiltered>,DEBUG,STATS ,INFORM,WARN  ,ERROR
    DEBUG -> DEBUG (output)
    STATS -> STAT (output)
    INFORM -> INFORM (output)
    WARN -> TestFilter
    WARN -> WARN (output)
    ERROR -> TestFilter
    ERROR -> ERROR (output)
Note: Sortie des messages (pour éventuelle utilisation)
DEBUG (output)
STAT (output)
INFORM (output)
WARN (output)
ERROR (output)
Note: Création d'un rapport HTML uniquement si l'utilisateur l'a demandé
TestFilter
    DEFAULT_VALUE = NO
    PASSED_TEST_GROUP_OUTPUT = FIRST
    TEST_LIST = "BOOL_OP,OR,COMPOSITE_TEST,""""""1"""""",TEST_CLAUSE,TEST $(html_repport) = YES",YES
    YES -> AttributeManager_2
Note: Génération d'une ligne de tableau HTML
AttributeManager_2
    ATTR_TABLE:
      SET_TO ligne_tableau (varchar(200)) = <tr>
        	<td>@DateTimeFormat(@Value(timestamp),%Y/%m/%d %H:%M:%S)</td>
        	<td>@Value(message)</td>
        </tr>
      REMOVE message (varchar(261))
    -> Aggregator
Note: Aggregation des lignes de tableau par niveau de message
Aggregator
    ACCUM_ATTRS_NAME = Drop Incoming Attributes
    CONCAT_ATTRS = ligne_tableau
    GROUP_BY = level
    MODE = Attributes Only
    SEP = "\n"
    AGGREGATE -> AttributeManager_3
Note: Génération d'un tableau HTML par niveau de message
AttributeManager_3
    ATTR_TABLE:
      SET_TO ligne_tableau (varchar(200)) = <h2>@Value(level)</h2>
        <table>
        <thead>
        	<tr>
        		<td>Horaire</td>
        		<td>Message</td>
        	</tr>
        </thead>
        <tbody>
        @Value(ligne_tableau)
        </tbody>
        </table>
    -> Aggregator_2
Note: Aggregation des différents tableaux
Aggregator_2
    ACCUM_ATTRS_NAME = Drop Incoming Attributes
    CONCAT_ATTRS = ligne_tableau
    MODE = Attributes Only
    SEP = "\n"
    AGGREGATE -> HTMLReportGenerator
Note: Génération d'une page web
HTMLReportGenerator
    CONTENT_LIST = HEADER HTML
    PAGE_CONFIG = HEADER{{TEXT;Rapport du fonctionnement du workspace FME;HEADER;H1;HEADER_ID;;ALIGNMENT;CENTER;COLOR;0,0,0;FME_CONTROLLER_QUERY_FILE;transformers/dependencies/html5/Header.fme;FME_CONTROLLER_CHOICE;Header}}HTML{{HTML;@Value(ligne_tableau);FME_CONTROLLER_QUERY_FILE;transformers/dependencies/html5/Custom HTML.fme;FME_CONTROLLER_CHOICE;Custom HTML}}
    TITLE = Rapport du fonctionnement du workspace FME
    -> FeatureWriter [HTML]
Note: Ecriture de la page web
FeatureWriter
    DATASET = $(FME_MF_DIR_ENCODED)rapport.html
    DATASET_ATTR = _dataset
    FEATURE_TYPE_LIST_ATTR = _feature_types
    FORMAT = HTML
    HTML_COORDINATE_SYSTEM_GRANULARITY = FEATURE
    HTML_DESTINATION_DATASETTYPE_VALIDATION = Yes
    HTML_ENCODING = UTF8
    HTML_END_OF_LINE = System
    HTML_MIME_TYPE = text/html
    HTML_OVERWRITE_FILE = YES
    HTML_WRITE_LAST_EOL = YES
    HTML_WRITE_UTF8_BOM = YES
    TOTAL_FEATURES_WRITTEN_ATTR = _total_features_written

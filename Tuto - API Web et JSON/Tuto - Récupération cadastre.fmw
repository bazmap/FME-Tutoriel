FME workspace Tuto - Récupération cadastre.fmw
Title: Tuto - Récupération cadastre

Parameters:
- layers = batiments,communes,parcelles   # Couches à récupérer
- entity = communes   # Type d'entité
- entity_code =   # Code de l'entité
- BDD_Dest =   # BDD de destination
- schema_dest =   # Schéma de destination
- srid_dest = EPSG:2154   # Système de coordonnées final

Writers:
- POSTGIS_1: POSTGIS to $(BDD_Dest)

Note: Récupération des données cadastrale basé sur l'API data.gouv.fr / https://cadastre.data.gouv.fr/datasets/cadastre-etalab / Plus d'info sur le service : / https://github.com/datagouv/cadastre-bundler-api/blob/master/definition.yml
Note: Initialisation
Creator
    GEOMTYPE = Geometry Object
    NUM = 1
    CREATED -> ParameterFetcher
Note: Récupération des paramètres
ParameterFetcher
    ATTR_LIST = layers $(layers) entity_code $(entity_code) entity $(entity)
    -> AttributeSplitter
Note: Création liste avec liste des couches
AttributeSplitter
    ATTR_NAME = layers
    DELIMITER = ,
    DROP_EMPTY_PARTS = NO
    LIST_NAME = layer
    TRIM_TYPE = BOTH
    -> ListExploder
Note: Création d'un objet par couche
ListExploder
    ATTR_ACCUM_MODE = Merge List Attributes
    ATTR_CONFLICT_RES_LOOKUP = INCOMING_IF_CONFLICT
    LIST_ATTR = layer{}
    ATTR_CONFLICT_RES = Use List Attribute Values
    ELEMENTS -> AttributeCreator
Note: Création requête
AttributeCreator
    ATTR_TABLE:
      SET_TO base_url (varchar(37)) = https://cadastre.data.gouv.fr/bundler
      SET_TO request (varchar(200)) = @Value(base_url)/cadastre-etalab/@Value(entity)/@Value(entity_code)/geojson/@Value(layer)
    -> HTTPCaller
Note: Récupération données
HTTPCaller
    CLIENT_CERTIFICATE_TYPE = NONE
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 5
    MINIMUM_ENCRYPTION_LEVEL = OS_DEFAULT
    REDIRECT_AUTH = ORIGINAL_DOMAIN_ONLY
    RESPONSE_HEADER_LIST_ATTR = _header
    RESPONSE_TYPE = Attribute
    RETRY_FAILED_TRANSFERS = CONNECTION 429 500 501 502 503 504 505 506 507 508 509 510 511
    RETRY_INITIAL_BACKOFF = 500
    RETRY_MAX_RETRIES = 1
    SPLIT_MULTIPART_DOWNLOADS = NO
    STATUS_CODE_ATTR = _http_status_code
    TARGET_ATTR = _response_body
    TARGET_ATTR_ENCODING = auto-detect
    TARGET_URL = @Value(request)
    TRANSFER_TIMEOUT_LENGTH = 90
    USE_COOKIES = No
    VERIFY_SSL_CERTIFICATES = Yes
    -> ListSearcher
Note: Récupération en-tête : type de données
ListSearcher
    ATTR_VALUE = content-type
    CASE = CASE_SENSITIVE
    INDEX_ATTR = _header_index
    LIST_ATTR = _header{}.name
    MATCHTYPE = FIRST_MATCHED_ENCODED
    FOUND -> TestFilter
TestFilter
    DEFAULT_VALUE = other
    PASSED_TEST_GROUP_OUTPUT = FIRST
    TEST_LIST = "BOOL_OP,OR,COMPOSITE_TEST,""""""1"""""",TEST_CLAUSE,TEST @Value(_header{@Value(_header_index)}.value) = application/vnd.geo+json",GeoJSON,"BOOL_OP,OR,COMPOSITE_TEST,""""""1"""""",TEST_CLAUSE,TEST @Value(_header{@Value(_header_index)}.value) = application/gzip",GZIP
    GeoJSON -> JSONFragmenter
    GZIP -> PythonCaller
Note: Dezippage
PythonCaller
    PYTHONSOURCE:
      # Import des modules FME
      import fmeobjects
      import fme
      import gzip
      import io


      class FeatureProcessor(object):

      	# Initialisation de la classe
      	def __init__(self):

      		#Définition variables
      		# Logger :
      		#   Utilisation : self.logger.logMessageString('Message', fmeobjects.FME_ERROR)
      		#   Niveau parmi : FME_INFORM, FME_WARN, FME_ERROR,  FME_FATAL
      		self.logger = fmeobjects.FMELogFile()



      	# Méthode appelée pour chaque objets (passé dans l'argument 'feature')
      	def input(self, feature):


      		# Ajout d'attributs
      		with gzip.GzipFile(fileobj=io.BytesIO(feature.getAttribute('_response_body'))) as gz:
      			feature.setAttribute(
      				"_response_body",
      				gz.read().decode('utf-8')
      			)

      		# Sortie de l'objet
      		self.pyoutput(feature)



      	# Fermeture de la classe
      	def close(self):
      		pass


      	# Méthode appelée pour chaque groupe (Group processing) après que tous les objets du groupe aient été traités
      	def process_group(self):
      		pass
    PYTHONSYMBOL = FeatureProcessor
    -> JSONFragmenter
Note: Découpage du json
JSONFragmenter
    EXPLODE_FORMAT = JSON
    EXTRACT_ATTR = No
    JSON_ATTR = _response_body
    JSON_QUERY = json["features"][*]
    READ_FROM_FILE = NO
    REJECT_EMPTY_LISTS = YES
    FRAGMENTS -> JSONFlattener
Note: Récupération attributs
JSONFlattener
    ERROR_LIST_ATTR = _json_error
    JSON_DOCUMENT = @Value(_response_body)
    NEW_ATTRIBUTES = geometry.coordinates{} buffer geometry.type buffer type buffer
    READ_FROM_FILE = NO
    RECURSIVE = YES
    -> JSONExtractor
Note: Récupération GeoJSON
JSONExtractor
    EXTRACT_QUERY_TABLE = geometry json["geometry"]
    JSON_DOCUMENT = @Value(_response_body)
    READ_FROM_FILE = NO
    EVALUATED -> GeometryReplacer
Note: Création géométrie
GeometryReplacer
    KIND = GEOJSON
    REMOVE_ATTRIBUTE = No
    SOURCE = @Value(geometry)
    KIND_LONG = GeoJSON
    -> Reprojector_2
Note: Reprojection données
Reprojector_2
    DEST = $(srid_dest)
    INTERPOLATION_TYPE = ,NearestNeighbor
    RASTER_CELL_SIZE_LOOKUP = ,PreserveCells
    RASTER_TOLERANCE = 0.0
    SOURCE = EPSG:4326
    INTERPOLATION_TYPE_NAME = Nearest Neighbor
    RASTER_CELL_SIZE = Preserve Cells
    REPROJECTED -> AttributeRemover
Note: Suppression attribut non utiles
AttributeRemover
    LIST_ATTRS = geometry.coordinates{} _header{} _header{}.name _header{}.value
    REMOVE_ATTRS = _http_status_code,_response_body,base_url,entity,entity_code,geometry,json_index,json_type,layers,request,geometry.type,type,_header_index
    -> BulkAttributeRenamer
Note: Renommage attribut "properties" du json initial
BulkAttributeRenamer
    ATTRCHOICE_ACTION = NONPROTECTEDFME
    CASE_DISP = YES
    MODE_CHOICE = RENAME
    PATTERN_ACTION_DISP = REMOVEPREFIX
    REPLACE_STR = properties.
    ATTRCHOICE = All Attributes
    -> SchemaScanner
Note: Génération du schéma
SchemaScanner
    CASE = No
    EMPTY_ATTR_HANDLING = SCANNER_DEFAULT
    GROUP_BY = layer
    HOLD = Yes
    IGNORE_REGEXP = layer
    MAX_FEATURES = 100
    NUMERIC_ALLOW_LEADING_ZEROES = Yes
    SCHEMA_NAME_ATTR = fme_feature_type_name
    TEST_STRING = Enter a string to test here...
    UNBOUNDED_NUMBERS = Yes
    UNBOUNDED_STRINGS = Yes
    -> Table1 (writer POSTGIS_1)
    <SCHEMA> -> Table1 (writer POSTGIS_1)
Table1 (writer POSTGIS_1)

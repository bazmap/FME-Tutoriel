FME workspace Tuto - Adresse BAN.fmw
Title: Tuto - Adresse BAN
Description: Le but de ce workspace est de récupérer les données de la base adresse de la BAN pour les stocker dans un geopackage.
Les données sont issues dun fichier CSV gzippé récupéré depuis la BAN.
La sortie se fait dans une table au sein d'un geopackage.
Startup Python:
      # Import des modules FME
      import fme
      import fmeobjects

      # Création d'un logger pour afficher les messages
      global_logger = fmeobjects.FMELogFile()

Parameters:
- temp_directory = C:\Users\abazin\Downloads   # Répertoire temporaire
- dept_number = 74   # Numéro de département
- DestDataset_OGCGEOPACKAGE = C:\Users\abazin\Downloads\ban.gpkg   # GeoPackage File

Writers:
- OGCGEOPACKAGE_1: OGCGEOPACKAGE to $(DestDataset_OGCGEOPACKAGE)

Note: Le but de ce workspace est de récupérer les données de la base adresse de la BAN pour les stocker dans un geopackage. / Les données sont issues dun fichier CSV gzippé récupéré depuis la BAN. / La sortie se fait dans une table au sein d'un geopackage.
Note: Initialisation
Creator
    GEOMTYPE = Geometry Object
    NUM = 1
    CREATED -> HTTPCaller_3
Note: Récupération des données depuis l'API
HTTPCaller_3
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 10
    MINIMUM_ENCRYPTION_LEVEL = OS_DEFAULT
    RATE_LIMIT_INTERVAL_IN_SECONDS = 1
    RATE_LIMIT_MAX_REQUESTS = 5
    RATE_LIMIT_REQUEST_TIMING = BURST
    REDIRECT_AUTH = ORIGINAL_DOMAIN_ONLY
    RESPONSE_TYPE = Attribute
    RETRY_FAILED_TRANSFERS = CONNECTION 429 500 501 502 503 504 505 506 507 508 509 510 511
    RETRY_INITIAL_BACKOFF = 500
    RETRY_MAX_RETRIES = 2
    SPLIT_MULTIPART_DOWNLOADS = NO
    STATUS_CODE_ATTR = _http_status_code
    TARGET_ATTR = _response_body
    TARGET_ATTR_ENCODING = auto-detect
    TARGET_URL = https://adresse.data.gouv.fr/data/ban/adresses/latest/csv/adresses-$(dept_number).csv.gz
    TRANSFER_TIMEOUT_LENGTH = 90
    USE_COOKIES = No
    VERIFY_SSL_CERTIFICATES = Yes
    -> PythonCaller
Note: Dégzippage des données / Parssage du CSV
PythonCaller
    HIDE_ATTRIBUTES = _creation_instance _http_status_code _response_body
    NEW_ATTRIBUTES = x buffer y buffer
    PYTHONSOURCE:
      # Import des modules FME non nécessaire car déjà fait dans le script au démarrage
      import io
      import gzip
      import csv

      class FeatureProcessor(object):

      	# Initialisation de la classe
      	def __init__(self):

      		# On réutilise des variables créées dans le script au démarrage

      		# Premier message
      		global_logger.logMessageString(
      			''.ljust(100, '-') + '\n' +
      			'PythonCaller '.ljust(100, '-') + '\n' +
      			''.ljust(100, '-'),
      			fmeobjects.FME_WARN
      		)



      	# Méthode appelée pour chaque objets (passé dans l'argument 'feature')
      	def input(self, feature):

      		# Ungzip data from httpcaller
      		with gzip.open(io.BytesIO(feature.getAttribute('_response_body')), 'rb') as gzip_file:
      			# Convert byte as text
      			with io.TextIOWrapper(gzip_file, encoding='utf-8') as decoded_file:
      				# Read CSV
      				csv_reader = csv.reader(decoded_file, delimiter=';')
      				# Get headers
      				csv_header = next(csv_reader)

      				for row in csv_reader:

      					# New object
      					newFeature = fmeobjects.FMEFeature()

      					# Add attributes
      					for index, column in enumerate(csv_header):
      						newFeature.setAttribute(
      							column,
      							row[index]
      						)

      					# Sortie de l'objet
      					self.pyoutput(newFeature)



      	# Fermeture de la classe
      	def close(self):

      		global_logger.logMessageString(
      			''.ljust(100, '-') + '\n' +
      			'PythonCaller '.ljust(100, '-') + '\n' +
      			''.ljust(100, '-'),
      			fmeobjects.FME_WARN
      		)
    PYTHONSYMBOL = FeatureProcessor
    -> VertexCreator
Note: Création de la géométrie
VertexCreator
    MEASURE_TYPE = Continuous
    MODE_NAME = Replace with Point
    XVAL = @Value(x)
    YVAL = @Value(y)
    -> CoordinateSystemSetter
Note: Attribution d'un système de coordonnées
CoordinateSystemSetter
    COORDSYS = EPSG:2154
    -> SchemaScanner
Note: Détection du schéma de la donnée
SchemaScanner
    CASE = No
    EMPTY_ATTR_HANDLING = SCANNER_DEFAULT
    HOLD = Yes
    IGNORE_REGEXP = ^(fme_)
    NUMERIC_ALLOW_LEADING_ZEROES = Yes
    SCHEMA_NAME_ATTR = fme_feature_type_name
    UNBOUNDED_NUMBERS = Yes
    UNBOUNDED_STRINGS = Yes
    -> FeatureJoiner [LEFT]
    <SCHEMA> -> FeatureJoiner [RIGHT]
Note: Chaque objet récupère son schéma associé
FeatureJoiner
    ATTR_CONFLICT_RES = Prefer Left
    GEOMETRY_HANDLING = Prefer Left
    JOIN_KEYS = fme_feature_type_name fme_feature_type_name AUTO
    JOIN_MODE = Left
    JOINED -> adresse (writer OGCGEOPACKAGE_1)
adresse (writer OGCGEOPACKAGE_1)

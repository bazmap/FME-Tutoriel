FME workspace Tuto - API Eau.fmw
Title: Tuto - API Eau
Description: Le but de ce workspace est de récupérer les paramètres physico-chimiques qui ont été analysé le long d'un cours d'eau : Le Risse (74)
Les données sont issues d'une API web.
La sortie se fait dans un tableau Excel

Parameters:
- DestDataset_XLSXW = $(FME_MF_DIR_USERTYPED)\resultat_analyse.xlsx   # Destination Microsoft Excel File

Writers:
- XLSXW_1: XLSXW to $(DestDataset_XLSXW)

Note: Initialisation
Note: Le but de ce workspace est de récupérer les paramètres physico-chimiques qui ont été analysé le long d'un cours d'eau : Le Risse (74) / Les données sont issues d'une API web. / La sortie se fait dans un tableau Excel
Creator
    GEOMTYPE = Geometry Object
    NUM = 1
    CREATED -> HTTPCaller
Note: Requête API / Request URL: https://hubeau.eaufrance.fr/api/v2/qualite_rivieres/analyse_pc / HTTP Method: GET / Query String Parameters: / code_cours_eau: V0150500 / size: 1 / page: 1
HTTPCaller
    ADDITIONAL_URL_PARAMETERS = code_cours_eau;V0150500 size;1 page;1
    CONNECTION_TIMEOUT_LENGTH = 60
    CUSTOM_HEADERS = Accept;application/json
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://hubeau.eaufrance.fr/api/v2/qualite_rivieres/analyse_pc
    TRANSFER_TIMEOUT_LENGTH = 90
    USE_COOKIES = No
    VERIFY_SSL_CERTIFICATES = Yes
    -> JSONExtractor
Note: Récupération du nombre d'élément total
JSONExtractor
    EXTRACT_QUERY_TABLE = nb_element json["count"]
    JSON_DOCUMENT = @Value(_response_body)
    READ_FROM_FILE = NO
    EVALUATED -> Cloner
Note: Génération d'un objet par page
Cloner
    COPIES = @ceil(@Evaluate(@Value(nb_element)/100), 0)
    COPYATT = page_num
    COPY -> HTTPCaller_2
Note: Récupération des données / Request URL: https://hubeau.eaufrance.fr/api/v2/qualite_rivieres/analyse_pc / HTTP Method: GET / Query String Parameters: / code_cours_eau: V0150500 / size: 100 / page: page_num + 1
HTTPCaller_2
    ADDITIONAL_URL_PARAMETERS = code_cours_eau;V0150500 size;100 page;@Evaluate(@Value(page_num)+1)
    CONNECTION_TIMEOUT_LENGTH = 60
    CUSTOM_HEADERS = Accept;application/json
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    RATE_LIMIT_INTERVAL_IN_SECONDS = 1
    RATE_LIMIT_MAX_REQUESTS = 5
    RATE_LIMIT_REQUEST_TIMING = BURST
    REDIRECT_AUTH = ORIGINAL_DOMAIN_ONLY
    RESPONSE_TYPE = Attribute
    RETRY_FAILED_TRANSFERS = CONNECTION 429 500 501 502 503 504 505 506 507 508 509 510 511
    RETRY_INITIAL_BACKOFF = 1000
    RETRY_MAX_RETRIES = 2
    SPLIT_MULTIPART_DOWNLOADS = NO
    STATUS_CODE_ATTR = _http_status_code
    TARGET_ATTR = _response_body
    TARGET_ATTR_ENCODING = auto-detect
    TARGET_URL = https://hubeau.eaufrance.fr/api/v2/qualite_rivieres/analyse_pc
    TRANSFER_TIMEOUT_LENGTH = 90
    USE_COOKIES = No
    VERIFY_SSL_CERTIFICATES = Yes
    -> JSONFragmenter
Note: Découpage des résultats / (100 résultats par page)
JSONFragmenter
    EXPLODE_FORMAT = JSON
    EXTRACT_ATTR = No
    JSON_ATTR = _response_body
    JSON_QUERY = json["data"][*]
    READ_FROM_FILE = NO
    REJECT_EMPTY_LISTS = YES
    FRAGMENTS -> JSONFlattener
Note: Récupération des attributs JSON en attributs "classiques"
JSONFlattener
    ERROR_LIST_ATTR = _json_error
    JSON_DOCUMENT = @Value(_response_body)
    READ_FROM_FILE = NO
    RECURSIVE = YES
    -> AttributeExposer
Note: Exposition de tous les attributs
AttributeExposer
    ATTR_TABLE = _http_status_code,uint8,_response_body,varchar(7865),agrement,varchar(200),code_accreditation,uint8,code_analyse,uint32,code_banque_reference,varchar(8),code_difficulte_analyse,uint8,code_fraction,uint8,code_groupe_parametre,varchar(200),code_groupe_parametre{0},uint8,code_groupe_parametre{1},uint8,code_groupe_parametre{2},uint8,code_groupe_parametre{3},uint8,code_groupe_parametre{4},uint8,code_groupe_parametre{5},uint8,code_groupe_parametre{6},uint8,code_groupe_parametre{7},uint8,code_groupe_parametre{8},uint8,code_groupe_parametre{9},uint8,code_groupe_parametre{10},uint8,code_groupe_parametre{11},uint8,code_groupe_parametre{12},uint8,code_groupe_parametre{13},uint8,code_groupe_parametre{14},uint8,code_groupe_parametre{15},uint8,code_groupe_parametre{16},uint8,code_groupe_parametre{17},uint8,code_groupe_parametre{18},uint8,code_groupe_parametre{19},uint8,code_groupe_parametre{20},uint8,code_groupe_parametre{21},uint8,code_groupe_parametre{22},uint8,code_groupe_parametre{23},uint8,code_groupe_parametre{24},uint8,code_groupe_parametre{25},uint8,code_groupe_parametre{26},uint8,code_groupe_parametre{27},uint8,code_groupe_parametre{28},uint8,code_groupe_parametre{29},uint8,code_groupe_parametre{30},uint8,code_groupe_parametre{31},uint8,code_groupe_parametre{32},uint8,code_groupe_parametre{33},uint8,code_groupe_parametre{34},uint8,code_groupe_parametre{35},uint8,code_groupe_parametre{36},uint8,code_insitu,uint8,code_laboratoire,uint64,code_methode_analyse,uint16,code_methode_extraction,uint16,code_methode_fractionnement,varchar(200),code_operation,uint64,code_parametre,uint16,code_point_eau_surface,uint8,code_prelevement,uint32,code_preleveur,uint64,code_producteur_analyse,uint64,code_qualification,uint8,code_remarque,uint8,code_reseau,varchar(200),code_station,uint32,code_statut,uint8,code_support,uint8,code_unite,uint16,commentaires_analyse,varchar(264),commentaires_resultat_analyse,varchar(200),date_analyse,varchar(10),date_maj_analyse,varchar(10),date_prelevement,varchar(10),geometry.coordinates{0},real64,geometry.coordinates{1},real64,geometry.crs.properties.name,varchar(29),geometry.crs.type,varchar(4),geometry.type,varchar(5),heure_analyse,varchar(200),heure_prelevement,varchar(8),incertitude_analytique,uint8,json_index,uint8,json_type,varchar(6),latitude,real64,libelle_fraction,varchar(50),libelle_groupe_parametre,varchar(200),libelle_groupe_parametre{0},varchar(73),libelle_groupe_parametre{1},varchar(32),libelle_groupe_parametre{2},varchar(107),libelle_groupe_parametre{3},varchar(136),libelle_groupe_parametre{4},varchar(230),libelle_groupe_parametre{5},varchar(230),libelle_groupe_parametre{6},varchar(234),libelle_groupe_parametre{7},varchar(234),libelle_groupe_parametre{8},varchar(234),libelle_groupe_parametre{9},varchar(234),libelle_groupe_parametre{10},varchar(234),libelle_groupe_parametre{11},varchar(230),libelle_groupe_parametre{12},varchar(230),libelle_groupe_parametre{13},varchar(234),libelle_groupe_parametre{14},varchar(234),libelle_groupe_parametre{15},varchar(234),libelle_groupe_parametre{16},varchar(220),libelle_groupe_parametre{17},varchar(204),libelle_groupe_parametre{18},varchar(209),libelle_groupe_parametre{19},varchar(203),libelle_groupe_parametre{20},varchar(191),libelle_groupe_parametre{21},varchar(191),libelle_groupe_parametre{22},varchar(191),libelle_groupe_parametre{23},varchar(191),libelle_groupe_parametre{24},varchar(191),libelle_groupe_parametre{25},varchar(110),libelle_groupe_parametre{26},varchar(191),libelle_groupe_parametre{27},varchar(191),libelle_groupe_parametre{28},varchar(191),libelle_groupe_parametre{29},varchar(191),libelle_groupe_parametre{30},varchar(191),libelle_groupe_parametre{31},varchar(81),libelle_groupe_parametre{32},varchar(79),libelle_groupe_parametre{33},varchar(65),libelle_groupe_parametre{34},varchar(191),libelle_groupe_parametre{35},varchar(47),libelle_groupe_parametre{36},varchar(12),libelle_insitu,varchar(11),libelle_parametre,varchar(59),libelle_qualification,varchar(8),libelle_station,varchar(19),libelle_support,varchar(3),limite_detection,real64,limite_quantification,real64,limite_saturation,varchar(200),longitude,real64,mnemo_accreditation,varchar(38),mnemo_difficulte_analyse,varchar(22),mnemo_remarque,varchar(63),mnemo_statut,varchar(52),nb_element,uint16,nom_laboratoire,varchar(72),nom_methode_analyse,varchar(261),nom_methode_extraction,varchar(33),nom_methode_fractionnement,varchar(200),nom_preleveur,varchar(72),nom_producteur_analyse,varchar(79),nom_reseau,varchar(200),page_num,uint8,rendement_extraction,varchar(200),resultat,real64,symbole_unite,varchar(9),uri_fraction,varchar(30),uri_groupe_parametre{0},varchar(30),uri_groupe_parametre{1},varchar(30),uri_groupe_parametre{2},varchar(31),uri_groupe_parametre{3},varchar(31),uri_groupe_parametre{4},varchar(31),uri_groupe_parametre{5},varchar(31),uri_groupe_parametre{6},varchar(31),uri_groupe_parametre{7},varchar(31),uri_groupe_parametre{8},varchar(31),uri_groupe_parametre{9},varchar(31),uri_groupe_parametre{10},varchar(31),uri_groupe_parametre{11},varchar(31),uri_groupe_parametre{12},varchar(31),uri_groupe_parametre{13},varchar(31),uri_groupe_parametre{14},varchar(31),uri_groupe_parametre{15},varchar(31),uri_groupe_parametre{16},varchar(31),uri_groupe_parametre{17},varchar(31),uri_groupe_parametre{18},varchar(31),uri_groupe_parametre{19},varchar(31),uri_groupe_parametre{20},varchar(31),uri_groupe_parametre{21},varchar(31),uri_groupe_parametre{22},varchar(31),uri_groupe_parametre{23},varchar(31),uri_groupe_parametre{24},varchar(31),uri_groupe_parametre{25},varchar(31),uri_groupe_parametre{26},varchar(31),uri_groupe_parametre{27},varchar(31),uri_groupe_parametre{28},varchar(31),uri_groupe_parametre{29},varchar(31),uri_groupe_parametre{30},varchar(31),uri_groupe_parametre{31},varchar(31),uri_groupe_parametre{32},varchar(31),uri_groupe_parametre{33},varchar(31),uri_groupe_parametre{34},varchar(31),uri_groupe_parametre{35},varchar(31),uri_groupe_parametre{36},varchar(31),uri_laboratoire,varchar(42),uri_methode_analyse,varchar(32),uri_methode_extraction,varchar(31),uri_methode_fractionnement,varchar(200),uri_parametre,varchar(32),uri_preleveur,varchar(42),uri_producteur_prelevement,varchar(42),uri_station,varchar(57),uri_support,varchar(29),uri_unite,varchar(31)
    -> AttributeManager
Note: Nettoyage attributs
AttributeManager
    ATTR_TABLE:
      REMOVE _response_body (buffer)
      REMOVE _http_status_code (buffer)
      REMOVE nb_element (varchar(200))
      REMOVE page_num (uint32)
      REMOVE json_type (buffer)
      REMOVE json_index (uint32)
      REMOVE agrement (varchar(200))
      REMOVE code_accreditation (uint8)
      REMOVE code_banque_reference (varchar(8))
      REMOVE code_difficulte_analyse (uint8)
      REMOVE code_fraction (uint8)
      REMOVE code_groupe_parametre (varchar(200))
      REMOVE code_groupe_parametre{0} (uint8)
      REMOVE code_groupe_parametre{1} (uint8)
      REMOVE code_groupe_parametre{2} (uint8)
      REMOVE code_groupe_parametre{3} (uint8)
      REMOVE code_groupe_parametre{4} (uint8)
      REMOVE code_groupe_parametre{5} (uint8)
      REMOVE code_groupe_parametre{6} (uint8)
      REMOVE code_groupe_parametre{7} (uint8)
      REMOVE code_groupe_parametre{8} (uint8)
      REMOVE code_groupe_parametre{9} (uint8)
      REMOVE code_groupe_parametre{10} (uint8)
      REMOVE code_groupe_parametre{11} (uint8)
      REMOVE code_groupe_parametre{12} (uint8)
      REMOVE code_groupe_parametre{13} (uint8)
      REMOVE code_groupe_parametre{14} (uint8)
      REMOVE code_groupe_parametre{15} (uint8)
      REMOVE code_groupe_parametre{16} (uint8)
      REMOVE code_groupe_parametre{17} (uint8)
      REMOVE code_groupe_parametre{18} (uint8)
      REMOVE code_groupe_parametre{19} (uint8)
      REMOVE code_groupe_parametre{20} (uint8)
      REMOVE code_groupe_parametre{21} (uint8)
      REMOVE code_groupe_parametre{22} (uint8)
      REMOVE code_groupe_parametre{23} (uint8)
      REMOVE code_groupe_parametre{24} (uint8)
      REMOVE code_groupe_parametre{25} (uint8)
      REMOVE code_groupe_parametre{26} (uint8)
      REMOVE code_groupe_parametre{27} (uint8)
      REMOVE code_groupe_parametre{28} (uint8)
      REMOVE code_groupe_parametre{29} (uint8)
      REMOVE code_groupe_parametre{30} (uint8)
      REMOVE code_groupe_parametre{31} (uint8)
      REMOVE code_groupe_parametre{32} (uint8)
      REMOVE code_groupe_parametre{33} (uint8)
      REMOVE code_groupe_parametre{34} (uint8)
      REMOVE code_groupe_parametre{35} (uint8)
      REMOVE code_groupe_parametre{36} (uint8)
      REMOVE code_insitu (uint8)
      REMOVE code_laboratoire (uint64)
      REMOVE code_methode_analyse (uint16)
      REMOVE code_methode_extraction (uint16)
      REMOVE code_methode_fractionnement (varchar(200))
      REMOVE code_operation (uint64)
      REMOVE code_parametre (uint16)
      REMOVE code_point_eau_surface (uint8)
      REMOVE code_prelevement (uint32)
      REMOVE code_preleveur (uint64)
      REMOVE code_producteur_analyse (uint64)
      REMOVE code_qualification (uint8)
      REMOVE code_remarque (uint8)
      REMOVE code_reseau (varchar(200))
      REMOVE code_station (uint32)
      REMOVE code_statut (uint8)
      REMOVE code_support (uint8)
      REMOVE code_unite (uint16)
      REMOVE commentaires_analyse (varchar(264))
      REMOVE commentaires_resultat_analyse (varchar(200))
      REMOVE date_analyse (varchar(10))
      REMOVE geometry.coordinates{0} (real64)
      REMOVE geometry.coordinates{1} (real64)
      REMOVE geometry.crs.properties.name (varchar(29))
      REMOVE geometry.crs.type (varchar(4))
      REMOVE geometry.type (varchar(5))
      REMOVE heure_analyse (varchar(200))
      REMOVE heure_prelevement (varchar(8))
      REMOVE incertitude_analytique (uint8)
      REMOVE libelle_fraction (varchar(50))
      REMOVE libelle_groupe_parametre (varchar(200))
      REMOVE libelle_groupe_parametre{0} (varchar(73))
      REMOVE libelle_groupe_parametre{1} (varchar(32))
      REMOVE libelle_groupe_parametre{2} (varchar(107))
      REMOVE libelle_groupe_parametre{3} (varchar(136))
      REMOVE libelle_groupe_parametre{4} (varchar(230))
      REMOVE libelle_groupe_parametre{5} (varchar(230))
      REMOVE libelle_groupe_parametre{6} (varchar(234))
      REMOVE libelle_groupe_parametre{7} (varchar(234))
      REMOVE libelle_groupe_parametre{8} (varchar(234))
      REMOVE libelle_groupe_parametre{9} (varchar(234))
      REMOVE libelle_groupe_parametre{10} (varchar(234))
      REMOVE libelle_groupe_parametre{11} (varchar(230))
      REMOVE libelle_groupe_parametre{12} (varchar(230))
      REMOVE libelle_groupe_parametre{13} (varchar(234))
      REMOVE libelle_groupe_parametre{14} (varchar(234))
      REMOVE libelle_groupe_parametre{15} (varchar(234))
      REMOVE libelle_groupe_parametre{16} (varchar(220))
      REMOVE libelle_groupe_parametre{17} (varchar(204))
      REMOVE libelle_groupe_parametre{18} (varchar(209))
      REMOVE libelle_groupe_parametre{19} (varchar(203))
      REMOVE libelle_groupe_parametre{20} (varchar(191))
      REMOVE libelle_groupe_parametre{21} (varchar(191))
      REMOVE libelle_groupe_parametre{22} (varchar(191))
      REMOVE libelle_groupe_parametre{23} (varchar(191))
      REMOVE libelle_groupe_parametre{24} (varchar(191))
      REMOVE libelle_groupe_parametre{25} (varchar(110))
      REMOVE libelle_groupe_parametre{26} (varchar(191))
      REMOVE libelle_groupe_parametre{27} (varchar(191))
      REMOVE libelle_groupe_parametre{28} (varchar(191))
      REMOVE libelle_groupe_parametre{29} (varchar(191))
      REMOVE libelle_groupe_parametre{30} (varchar(191))
      REMOVE libelle_groupe_parametre{31} (varchar(81))
      REMOVE libelle_groupe_parametre{32} (varchar(79))
      REMOVE libelle_groupe_parametre{33} (varchar(65))
      REMOVE libelle_groupe_parametre{34} (varchar(191))
      REMOVE libelle_groupe_parametre{35} (varchar(47))
      REMOVE libelle_groupe_parametre{36} (varchar(12))
      REMOVE libelle_insitu (varchar(11))
      REMOVE libelle_support (varchar(3))
      REMOVE limite_detection (real64)
      REMOVE limite_quantification (real64)
      REMOVE limite_saturation (varchar(200))
      REMOVE mnemo_accreditation (varchar(38))
      REMOVE mnemo_difficulte_analyse (varchar(22))
      REMOVE mnemo_statut (varchar(52))
      REMOVE nom_laboratoire (varchar(72))
      REMOVE nom_methode_analyse (varchar(261))
      REMOVE nom_methode_extraction (varchar(33))
      REMOVE nom_methode_fractionnement (varchar(200))
      REMOVE nom_preleveur (varchar(72))
      REMOVE nom_producteur_analyse (varchar(79))
      REMOVE nom_reseau (varchar(200))
      REMOVE rendement_extraction (varchar(200))
      REMOVE uri_fraction (varchar(30))
      REMOVE uri_groupe_parametre{0} (varchar(30))
      REMOVE uri_groupe_parametre{1} (varchar(30))
      REMOVE uri_groupe_parametre{2} (varchar(31))
      REMOVE uri_groupe_parametre{3} (varchar(31))
      REMOVE uri_groupe_parametre{4} (varchar(31))
      REMOVE uri_groupe_parametre{5} (varchar(31))
      REMOVE uri_groupe_parametre{6} (varchar(31))
      REMOVE uri_groupe_parametre{7} (varchar(31))
      REMOVE uri_groupe_parametre{8} (varchar(31))
      REMOVE uri_groupe_parametre{9} (varchar(31))
      REMOVE uri_groupe_parametre{10} (varchar(31))
      REMOVE uri_groupe_parametre{11} (varchar(31))
      REMOVE uri_groupe_parametre{12} (varchar(31))
      REMOVE uri_groupe_parametre{13} (varchar(31))
      REMOVE uri_groupe_parametre{14} (varchar(31))
      REMOVE uri_groupe_parametre{15} (varchar(31))
      REMOVE uri_groupe_parametre{16} (varchar(31))
      REMOVE uri_groupe_parametre{17} (varchar(31))
      REMOVE uri_groupe_parametre{18} (varchar(31))
      REMOVE uri_groupe_parametre{19} (varchar(31))
      REMOVE uri_groupe_parametre{20} (varchar(31))
      REMOVE uri_groupe_parametre{21} (varchar(31))
      REMOVE uri_groupe_parametre{22} (varchar(31))
      REMOVE uri_groupe_parametre{23} (varchar(31))
      REMOVE uri_groupe_parametre{24} (varchar(31))
      REMOVE uri_groupe_parametre{25} (varchar(31))
      REMOVE uri_groupe_parametre{26} (varchar(31))
      REMOVE uri_groupe_parametre{27} (varchar(31))
      REMOVE uri_groupe_parametre{28} (varchar(31))
      REMOVE uri_groupe_parametre{29} (varchar(31))
      REMOVE uri_groupe_parametre{30} (varchar(31))
      REMOVE uri_groupe_parametre{31} (varchar(31))
      REMOVE uri_groupe_parametre{32} (varchar(31))
      REMOVE uri_groupe_parametre{33} (varchar(31))
      REMOVE uri_groupe_parametre{34} (varchar(31))
      REMOVE uri_groupe_parametre{35} (varchar(31))
      REMOVE uri_groupe_parametre{36} (varchar(31))
      REMOVE uri_laboratoire (varchar(42))
      REMOVE uri_methode_analyse (varchar(32))
      REMOVE uri_methode_extraction (varchar(31))
      REMOVE uri_methode_fractionnement (varchar(200))
      REMOVE uri_parametre (varchar(32))
      REMOVE uri_preleveur (varchar(42))
      REMOVE uri_producteur_prelevement (varchar(42))
      REMOVE uri_station (varchar(57))
      REMOVE uri_support (varchar(29))
      REMOVE uri_unite (varchar(31))
      REMOVE code_groupe_parametre{} (varchar(200))
      REMOVE geometry.coordinates{} (varchar(200))
      REMOVE libelle_groupe_parametre{} (varchar(200))
      REMOVE uri_groupe_parametre{} (varchar(200))
    -> Sorter
Note: Tri des résultats par date de prélèvement
Sorter
    SORT_PARM = date_prelevement NATURAL ASCENDING
    SORTED -> analyse (writer XLSXW_1)
Note: Ecriture des données
analyse (writer XLSXW_1)
    attributes: code_analyse number(20), date_prelevement auto, date_maj_analyse auto, latitude number(20), longitude number(20), libelle_station auto, libelle_parametre auto, resultat number(20), symbole_unite auto, libelle_qualification auto, mnemo_remarque auto

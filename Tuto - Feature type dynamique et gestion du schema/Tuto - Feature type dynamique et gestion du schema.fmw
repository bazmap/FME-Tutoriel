FME workspace Tuto - Feature type dynamique et gestion du schema.fmw
Title: Dynamic feature type and schema management
Description: Le but de ce workspace est de démontrer les possibilités de FME pour lire et écrire des données de façon dynamique, sans forcément connaitre la structure des données.
Il n'y a pas de but précis sur ce workspace, uniquement des techniques.
Plus d'infos sur le site de Safe : https://community.safe.com/s/article/dynamic-workflow-tutorial-introduction
Les données sont issues de fichiers CSV.
La sortie se fait dans plusieurs fichiers CSV.

Parameters:
- data_input_source = $(FME_MF_DIR_USERTYPED)\data_input\*.csv   # CSV/Compressed_CSV/TEXT_Files(*.csv) Emplacement des données pour le reader "data_input" 
- data_output_dest = $(FME_MF_DIR_USERTYPED)\data_output   # Emplacement des données pour le writer data_output 
- data_structure_source = $(FME_MF_DIR_USERTYPED)\data_structure\*.csv   # CSV/Compressed_CSV/TEXT_Files(*.csv) Emplacmeent des données pour le reader "data_structure" 
- data_input_dynamique_source = $(FME_MF_DIR_USERTYPED)\data_input\*.csv   # CSV/Compressed_CSV/TEXT_Files(*.csv) Emplacement des données pour le reader "data_input_dynamique" 
- FEATURE_TYPES =

Readers:
- CSV2_1: CSV2 from $(data_input_source)
- CSV2_2: CSV2 from $(data_structure_source)
- CSV2_3: CSV2 from $(data_input_dynamique_source)

Writers:
- CSV2_4: CSV2 to $(data_output_dest)

Note: Le but de ce workspace est de démontrer les possibilités de FME pour lire et écrire des données de façon dynamique, sans forcément connaitre la structure des données. / Il n'y a pas de but précis sur ce workspace, uniquement des techniques. / Plus d'infos sur le site de Safe : https://community.safe.com/s/article/dynamic-workflow-tutorial-introduction / Les données sont issues de fichiers CSV. / La sortie se fait dans plusieurs fichiers CSV.
Note: Cette partie décrit comment FME peut lire des données de façon dynamqiue : sans forcément connaitre le schéma (la structure) de la donnée. / Cela permet de lire un lot de tables sans en connaitre leurs structures.
Note: Lecture "classique" : deux tables = deux features types / Chaque table possède ses propres attributs / On récupère la colonne fme_feature_type qui contient le nom du feature_type (la table)
data_input - table A (reader CSV2_1)
    attributes: colonne_A1 uint8, colonne_A2 string, colonne_X string
    -> AttributeManager
data_input - table B (reader CSV2_1)
    attributes: colonne_B1 uint8, colonne_B2 string, colonne_X string
    -> AttributeManager
Note: Non utile, uniquement présent pour visualiser les colonnes
AttributeManager
    -> Junction
Note: L'utilisation d'un feature type dynamique permet de récupérer les objets de plusieurs tables en une seule fois
data_input - table A (reader CSV2_3)
    attributes: colonne_A1 uint8, colonne_A2 string, colonne_X string, colonne_B1 uint8, colonne_B2 string
    -> AttributeManager_2
Note: Non utile, uniquement présent pour visualiser les colonnes
AttributeManager_2
    -> Junction [off]
Note: Il est ici possible d'utiliser la sortie de l'un ou l'autre des AttributeManager : le résultat est identique. / L'une des branche a été désactivée.
Junction
    -> Junction_4
    -> Junction_8
    -> Junction_5
    -> Junction_3
    -> Junction_6
    -> Junction_7
    -> Junction_2
Note: Cette partie décrit comment FME peut écrire des données de façon dynamqiue : sans fixer le schéma (la structure) de la donnée. / Cela permet d'écrire un lot de tables sans avoir à définir manuellement leurs structures, FME va la créer pour nous.
Junction_2
    -> table_100 (writer CSV2_4)
Note: Test 1 : / Fichiers : résultat_1_xxx / Le schéma est créé automatiquement par FME en fonction des attributs qui arrivent dans le feature type. / => Les couches de destination possèdent toute la même structure basée sur la structure globale visible dans FME : toutes les données sont transférées.
table_100 (writer CSV2_4)
    attributes: colonne_A1 uint8, colonne_A2 string, colonne_X string, colonne_B1 uint8, colonne_B2 string
Junction_8
    -> table_1 (writer CSV2_4)
Note: Test 2 : / Fichiers : résultat_2_xxx / Récupération du schéma depuis la table initiale : / - Schema source : "data_input" => le reader utilisé pour lire les données utilisées dans ce workspace / - Schema définition name : champ fme_feature_type => nom de la table d'origine des données : chaque données imposera une structure spécifique à sa table de destination. / => Les couches de destination possèdent la même structure que les données d'entrées : toutes les données sont transférées. Chaque table possède sa propre structure.
table_1 (writer CSV2_4)
Junction_7
    -> table_2 (writer CSV2_4)
Note: Test 3 : / Fichiers : résultat_3_xxx / Récupération du schéma depuis un fichier externe : / - Schema source : "data_structure" (reader "ressource" permettant de lire la structure d'une donnée pour l'utiliser dans FME) / - Schema définition name : "data_structure - structure 2" (nom de la table lue par le reader "data_structure" dont la structure doit être reproduite) / => Les couches de destination possèdent une structure identique pour chaque couche car la valeur de schema définition name est fixe. Les données d'entrées sont transférées uniquement dans les attributs de même nom (donc aucune données des colonnes A1 et A2 car la structure choisie (data_structure - structure 2) ne possède que les colonnes B1, B2 et X).
table_2 (writer CSV2_4)
Junction_6
    -> AttributeCreator_2
Note: Selon le nom de table d'origine on attribut une structure à utiliser avec une valeur conditionnelle : / data_input - table A : data_structure - structure 1 / data_input - table B : data_structure - structure 2
AttributeCreator_2
    ATTR_TABLE = SET_TO structure (varchar(200)) = FME_CONDITIONAL:DEFAULT_VALUE'_FME_NO_OP_'BOOL_OP;OR;COMPOSITE_TEST;1;TEST @Value(fme_feature_type) = data_input - table A'data_structure - structure 1'BOOL_OP;OR;COMPOSITE_TEST;1;TEST @Value(fme_feature_type) = data_input - table B'data_structure - structure 2'FME_NUM_CONDITIONS3___
    -> table_3 (writer CSV2_4)
Note: Test 4 : / Fichiers : résultat_4_xxx / Récupération du schéma depuis un fichier externe : / - Schéma source : "data_structure" (reader "ressource" permettant de lire la structure d'une donnée pour l'utiliser dans FME) / - Schéma définition name : champ "structure" / => Les couches de destination possèdent une structure variable : selon la valeur du champ "structure", la structure sera celle d'une table ou d'une autre lue par le reader ressource "data_structure". Les données d'entrées sont transférées uniquement dans les attributs de même nom.
table_3 (writer CSV2_4)
Junction_5
    -> AttributeCreator
Note: Description manuelle de la structure : / Il est possible de décrire la structure manuellement en ajoutant une liste "attribute" structurée comme suivant : / - attribute{0}.fme_data_type : type de données / - attribute{0}.name : nom du champ
AttributeCreator
    ATTR_TABLE:
      SET_TO attribute{0}.fme_data_type (varchar(200)) = fme_varchar(100)
      SET_TO attribute{0}.name (varchar(200)) = colonne_A1
      SET_TO attribute{1}.fme_data_type (varchar(200)) = fme_varchar(100)
      SET_TO attribute{1}.name (varchar(200)) = colonne_A2
      SET_TO attribute{2}.fme_data_type (varchar(200)) = fme_varchar(100)
      SET_TO attribute{2}.name (varchar(200)) = colonne_X
    -> table_300 (writer CSV2_4)
Note: Test 5 : / Fichiers : résultat_5_xxx / Récupération du schéma depuis les objets : / - Schéma source : "Schema From Schema Feature" (on va cherche la définition du schéma stockée dans l'objet) / - Schéma définition name : non nécessaire / => Les couches de destination possèdent une structure fixe car la définition est la même pour chaque objet. Les données d'entrées sont transférées uniquement dans les attributs de même nom (donc aucune donnée dans les colonnes B1 et B2).
table_300 (writer CSV2_4)
Junction_4
    -> SchemaScanner
Note: Déclaration automatique de la structure : / Le transformer récupère la structure de chaque objet automatiquement. / Les champs commençant par "multi_reader" "csv_" et "fme_" ne sont pas repris car inutiles dans la table finale. / Ont groupe selon le champ fme_feature_type pour générer un schéma spécifique par table source de données.
SchemaScanner
    CASE = No
    EMPTY_ATTR_HANDLING = IGNORE
    GROUP_BY = fme_feature_type
    HOLD = Yes
    IGNORE_REGEXP = ^(multi_reader|csv_|fme_)
    NUMERIC_ALLOW_LEADING_ZEROES = Yes
    SCHEMA_NAME_ATTR = fme_feature_type_name
    TEST_STRING = Enter a string to test here...
    UNBOUNDED_NUMBERS = Yes
    UNBOUNDED_STRINGS = No
    -> FeatureJoiner [LEFT]
    <SCHEMA> -> FeatureJoiner [RIGHT]
Note: Chaque objet récupère son schéma associé
FeatureJoiner
    ATTR_CONFLICT_RES = Prefer Left
    GEOMETRY_HANDLING = Prefer Left
    JOIN_KEYS = fme_feature_type_name fme_feature_type_name AUTO
    JOIN_MODE = Left
    JOINED -> table_30000 (writer CSV2_4)
Note: Test 6 : / Fichiers : résultat_6_xxx / Récupération du schéma depuis les objets : / - Schéma source : "Schema From Schema Feature" (on va cherche la définition du schéma stockée dans l'objet) / - Schéma définition name : non nécessaire / => Les couches de destination possèdent une structure variable issue de chaque objet. Les données sont donc toutes transférées car les attributs de destination possèdent des noms correspondants.
table_30000 (writer CSV2_4)
Junction_3
    -> NullAttributeMapper
Note: Ce transformers permet de "fixer" les attributs ayant le statut "missing" en leur attribuant la valeur "NULL".
NullAttributeMapper
    ATTRCHOICE = Selected Attributes
    ATTRLIST = colonne_A1 colonne_A2 colonne_B1 colonne_B2
    NULL_TREATMENT = Null
    SOURCE_ATTR_VAL = "Missing (Selected Attributes Only)"
    -> SchemaScanner_2
Note: Déclaration automatique de la structure
SchemaScanner_2
    CASE = No
    EMPTY_ATTR_HANDLING = IGNORE
    GROUP_BY = fme_feature_type
    HOLD = Yes
    IGNORE_REGEXP = ^(multi_reader|csv_|fme_)
    NUMERIC_ALLOW_LEADING_ZEROES = Yes
    SCHEMA_NAME_ATTR = fme_feature_type_name
    TEST_STRING = Enter a string to test here...
    UNBOUNDED_NUMBERS = Yes
    UNBOUNDED_STRINGS = No
    -> FeatureJoiner_2 [LEFT]
    <SCHEMA> -> FeatureJoiner_2 [RIGHT]
Note: Chaque objet récupère son schéma associé
FeatureJoiner_2
    ATTR_CONFLICT_RES = Prefer Left
    GEOMETRY_HANDLING = Prefer Left
    JOIN_KEYS = fme_feature_type_name fme_feature_type_name AUTO
    JOIN_MODE = Left
    JOINED -> table_3000000 (writer CSV2_4)
Note: Test 7 : / Fichiers : résultat_7_xxx / Récupération du schéma depuis les objets : / - Schéma source : "Schema From Schema Feature" (on va cherche la définition du schéma stockée dans l'objet) / - Schéma définition name : non nécessaire / => Les couches de destination possèdent une structure variable issue de chaque objet. Les données sont donc toutes transférées car les attributs de destination possèdent des noms correspondants. Tous les attributs visibles dans FME sont ajoutés à toutes les tables de destination (A1, A2, B1, B2 et X).
table_3000000 (writer CSV2_4)

Bookmark: Lecture dynamique
Note: L'utilisation d'un feature type dynamqiue ou de plusieurs features types dont on fusionne les sorties (comme ici) produit le même résultat. / D'après la visualisation sur le workspace, les objets possèdent les attributs suivants : / - colonne_A1 / - colonne_A2 / - colonne_B1 / - colonne_B2 / - colonne_X / - fme_feature_type / En réalité, les données en provenance de la table A possèdent les attributs suivants : / - colonne_A1 / - colonne_A2 / - colonne_X / - fme_feature_type / les données en provenance de la table B possèdent les attributs suivants : / - colonne_B1 / - colonne_B2 / - colonne_X / - fme_feature_type / Vous pouvez le voir de part le statut "missing" des attributs en provenance de l'autre table lorsque vous inspectez les objets.

Bookmark: Sortie dynamique
Note: La structure des features types est dynamique : FME la créé à la volée en fonction des paramètres qui sont renseignés. / Ainsi, pour chaque couche de donnée produite, la structure peut être identique entre les couches ou différentes pour chaque couche. / Dans le cadre d'un writer dynamique, on utilise un mappage de champ automatique : les données ne sont écrites que si elle sont contenues dans un attribut dont le nom est présent dans la structure de la destination / Trois paramètres sont modifiés dans les features types suivants : / - CSV File Name : nom du fichier CSV / - Schema sources : Emplacement de stockage des définitions des structures à reproduire, cela peut être : / - Un reader : en lisant les données à importer dans le workspace, le reader lit également la structure des données. / - Un reader ressource : il s'agit d'un reader dédié uniquement à la lecture des structures, il n'importera pas de données dans le workspace. / - From schema feature : récupération de la structure portée par l'objet : il faut alors déclarer pour chaque objet la structure qu'il possède. / - Schema definition name : nom de la table présente dans le reader listé dans schema sources dont la structure doit être reproduite

FME workspace Tuto - Listing des remontées mécaniques.fmw
Title: Tuto - Listing des remontées mécaniques
Description: Le but de ce workspace est de récupérer pour chaque commune de Haute-Savoie, une liste des remontées mécaniques qui sont présentes et de réaliser quelques statistiques dessus.
Les données sont issues d'un geopackage.
Aucune sortie n'est prévue dans le script.

Parameters:
- SourceDataset_OGCGEOPACKAGE = $(FME_MF_DIR_USERTYPED)\data_liste.gpkg   # GeoPackage File

Readers:
- OGCGEOPACKAGE_1: OGCGEOPACKAGE from $(SourceDataset_OGCGEOPACKAGE)

Note: Le but de ce workspace est de récupérer pour chaque commune de Haute-Savoie, une liste des remontées mécaniques qui sont présentes et de réaliser quelques statistiques dessus. / Les données sont issues d'un geopackage. / Aucune sortie n'est prévue dans le script.
communes (reader OGCGEOPACKAGE_1)
    attributes: id text, nom text, population text, code_postal text, code_insee text, id_0 int,PrimaryKey
    -> SpatialRelator [Requestor]
remontees_mecaniques (reader OGCGEOPACKAGE_1)
    attributes: id text, nom text, type text, capacite_horaire text, capacite_vehicule text, id_0 int,PrimaryKey
    -> SpatialRelator [Supplier]
Note: Générer une liste des RM intersectants chaque commune
SpatialRelator
    AGGREGATE_HANDLING = Yes
    CALC_CARD = No
    CURVE_BOUNDARY_RULE_PARAM = Default Rule
    LIST_NAME = remontee_mecanique
    PREDICATES = INTERSECTS
    SUCCESS_ATTR = nb_remontee
    -> ListElementCounter
Note: Compter le nombre de RM
ListElementCounter
    CNT_ATTR = nb_remontee
    LIST_NAME = remontee_mecanique{}
    -> ListHistogrammer
Note: Nombre de RM par type
ListHistogrammer
    LIST_NAME = rm_histogram
    SRC_LIST = remontee_mecanique{}.type
    -> ListConcatenator
Note: Générer une liste des types de RM
ListConcatenator
    DROP_EMPTY_PARTS = Yes
    LIST_ATTR = remontee_mecanique{}.type
    SEP = ", "
    VAL_ATTR = liste_type_rm
    -> ListSorter
Note: Trier les éléments d'une liste
ListSorter
    ORDER = Descending
    SRC_LIST = remontee_mecanique{}.capacite_horaire
    TYPE = Numeric
    -> AttributeManager
Note: Récupérer la valeur du premier élément d'une liste
AttributeManager
    ATTR_TABLE:
      SET_TO capacite_max (varchar(200)) = @Value(remontee_mecanique{0}.capacite_horaire)
      SET_TO capacite_min (varchar(200))
      SET_TO = @Value(remontee_mecanique{@evaluate(@Value(nb_remontee)-1)}.capacite_horaire)
    -> ListSummer
Note: Calculer la somme des capacités
ListSummer
    RESULT = rm_capacite_totale
    SRC_LIST = remontee_mecanique{}.capacite_horaire
    -> AttributeManager_2
Note: Calculer la capacité moyenne (somme/nb)
AttributeManager_2
    ATTR_TABLE = SET_TO rm_capacite_moyenne (real64) = @Evaluate(@Value(rm_capacite_totale)/@Value(nb_remontee))
    -> ListRangeExtractor
Note: Capacités minimum et maximum
ListRangeExtractor
    MAX = rm_capacite_max
    MIN = rm_capacite_min
    SRC_LIST = remontee_mecanique{}.capacite_horaire

FME workspace Tuto - Attributs de listes.fmw

Parameters:
- SourceDataset_OGCGEOPACKAGE = $(FME_MF_DIR)data_liste.gpkg   # GeoPackage File

Readers:
- OGCGEOPACKAGE_1: OGCGEOPACKAGE from $(SourceDataset_OGCGEOPACKAGE)

communes (reader OGCGEOPACKAGE_1)
    attributes: id text, nom text, population text, code_postal text, code_insee text, id_0 int,PrimaryKey
    -> LineOnAreaOverlayer [AREA]
    -> SpatialRelator [Requestor]
remontees_mecaniques (reader OGCGEOPACKAGE_1)
    attributes: id text, nom text, type text, capacite_horaire text, capacite_vehicule text, id_0 int,PrimaryKey
    -> LineOnAreaOverlayer [LINE]
    -> SpatialRelator [Supplier]
Note: Autre possibilitée
LineOnAreaOverlayer
    CANDIDATE_LIST_ATTRS_TO_INCLUDE_MODE = All Attributes
    CANDIDATE_LIST_NAME = remontee_mecanique
    CLEANING_TOLERANCE = Automatic
    DEAGGREGATE_INPUT = Yes
    OVERLAY_TYPE = LINE_ON_AREA
    OV_ATTR = nb_remontee
Note: Générer une liste des RM intersectants chaque commune
SpatialRelator
    AGGREGATE_HANDLING = Yes
    CALC_CARD = No
    CURVE_BOUNDARY_RULE_PARAM = Default Rule
    LIST_NAME = remontee_mecanique
    PREDICATES = INTERSECTS
    SUCCESS_ATTR = nb_remontee
    -> ListElementCounter
Note: Compter le nombre de RM
ListElementCounter
    CNT_ATTR = nb_remontee
    LIST_NAME = remontee_mecanique{}
    -> ListHistogrammer
Note: Nombre de RM par type
ListHistogrammer
    LIST_NAME = rm_histogram
    SRC_LIST = remontee_mecanique{}.type
    -> ListConcatenator
Note: Générer une liste des types de RM
ListConcatenator
    DROP_EMPTY_PARTS = Yes
    LIST_ATTR = remontee_mecanique{}.type
    SEP = ", "
    VAL_ATTR = liste_type_rm
    -> ListSorter
Note: Trier les éléments d'une liste
ListSorter
    ORDER = Descending
    SRC_LIST = remontee_mecanique{}.capacite_horaire
    TYPE = Numeric
    -> AttributeManager
Note: Récupérer la valeur du premier élément d'une liste
AttributeManager
    ATTR_TABLE:
      SET_TO capacite_max (varchar(200)) = @Value(remontee_mecanique{0}.capacite_horaire)
      SET_TO capacite_min (varchar(200))
      SET_TO = @Value(remontee_mecanique{@evaluate(@Value(nb_remontee)-1)}.capacite_horaire)
    -> ListSummer
Note: Calculer la somme des capacités
ListSummer
    RESULT = rm_capacite_totale
    SRC_LIST = remontee_mecanique{}.capacite_horaire
    -> AttributeManager_2
Note: Calculer la capacité moyenne (somme/nb)
AttributeManager_2
    ATTR_TABLE = SET_TO rm_capacite_moyenne (real64) = @Evaluate(@Value(rm_capacite_totale)/@Value(nb_remontee))
    -> ListRangeExtractor
Note: Capacités minimum et maximum
ListRangeExtractor
    MAX = rm_capacite_max
    MIN = rm_capacite_min
    SRC_LIST = remontee_mecanique{}.capacite_horaire
observation_oiseaux (reader OGCGEOPACKAGE_1)
    attributes: lieu text, date text, temp_moy float, espece_vue text, id int,PrimaryKey
    -> AttributeSplitter_2
Note: Créer une liste à partir d'un attribut avec valeurs délimitées
AttributeSplitter_2
    ATTR_NAME = espece_vue
    DELIMITER = ,
    DROP_EMPTY_PARTS = YES
    LIST_NAME = espece
    TRIM_TYPE = BOTH
    -> ListBuilder_3
Note: Grouper les objets en listes selon un attribut
ListBuilder_3
    GROUP_BY = lieu
    LIST_ATTRS_TO_INCLUDE = date temp_moy espece_vue espece{}
    LIST_NAME = data
    -> ListRangeExtractor_3
Note: Extraire les données min et max
ListRangeExtractor_3
    MAX = temp_max
    MIN = temp_min
    SRC_LIST = data{}.temp_moy
    -> ListRenamer_2
Note: Renommer des attributs de liste
ListRenamer_2
    LEAVE_ORIG = No
    LIST_ACTION = Rename
    LIST_COMPONENT_NAMES = data{},data{},espece_vue,espece_observee
    LIST_NAME = data{}.espece_vue
    -> ListSearcher_3
Note: Rechercher des objets contenant une valeur dans un élément de liste
ListSearcher_3
    ATTR_VALUE = mésange
    CASE = CASE_SENSITIVE
    INDEX_ATTR = index_presence
    LIST_ATTR = data{}.espece_observee
    MATCHTYPE = REGULAR_EXPRESSION_ENCODED
observation_oiseaux_02 (reader OGCGEOPACKAGE_1)
    attributes: lieu text(9), jour_1_temp_moy float, jour_1_espece_vue text(37), jour_2_temp_moy float, jour_2_espece_vue text(37), jour_3_temp_moy float, jour_3_espece_vue text(37), jour_4_temp_moy float, jour_4_espece_vue text(37), jour_5_temp_moy float, jour_5_espece_vue text(37), id int,PrimaryKey
    -> ListExpressionPopulator
Note: Création d'une liste pour chaque objets à partir d'une série d'attributs / => Température
ListExpressionPopulator
    EXPRESSION = jour_([0-9])_temp_moy
    LIST_NAME = temp_moy
    -> ListExpressionPopulator_2
Note: Création d'une liste pour chaque objets à partir d'une série d'attributs / => Espèce vue
ListExpressionPopulator_2
    EXPRESSION = jour_([0-9])_espece_vue
    LIST_NAME = espece_vue
    -> ListConcatenator_2
Note: Concaténer tous les éléments d'une liste dans un attribut
ListConcatenator_2
    DROP_EMPTY_PARTS = No
    LIST_ATTR = espece_vue{}
    SEP = ,
    VAL_ATTR = espece_vue
    -> AttributeSplitter_3
Note: Créer une liste à partir d'un attribut avec valeurs délimitées : liste d'espèces vues
AttributeSplitter_3
    ATTR_NAME = espece_vue
    DELIMITER = ,
    DROP_EMPTY_PARTS = NO
    LIST_NAME = espece_vue_total
    TRIM_TYPE = BOTH
    -> BulkAttributeRemover
Note: Suppression des attributs non utiles
BulkAttributeRemover
    ATTR_EXP = jour_
    -> ListHistogrammer_2
Note: Nombre d'observations par espèce
ListHistogrammer_2
    LIST_NAME = espece_histogram
    SRC_LIST = espece_vue_total{}
    -> ListDuplicateRemover
Note: Suppression des éléments en doublon dans les listes
ListDuplicateRemover
    SRC_LIST = espece_vue_total{}

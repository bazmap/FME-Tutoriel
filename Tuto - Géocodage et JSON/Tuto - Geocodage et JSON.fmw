FME workspace Tuto - Geocodage et JSON.fmw

Parameters:
- SourceDataset_CSV2 = $(FME_MF_DIR)base_adresse.csv   # Source CSV (Comma Separated Value) File(s)

Readers:
- CSV2_1: CSV2 from $(SourceDataset_CSV2)

base_adresse (reader CSV2_1)
    attributes: Number uint8, Street string, Postcode uint32, City string, Country string
    -> Counter
Counter
    CNT_ATTR = id
    DOMAIN = counter
    SCOPE = Global
    START = 0
    -> HTTPCaller
    -> Geocoder
Note: Requête HTTP : / On intérroge l'API OpenStreetMap de géocodage : / - URL : https://nominatim.openstreetmap.org/ / - Paramètres : / - format : JSON / - q : adresse du point / - adressdetails : récupération des infos sur le point geocodé / La réponse est stockée dans le champ _reponse_body
HTTPCaller
    ADDITIONAL_URL_PARAMETERS = format;json q;@Value(Number), @Value(Street), @Value(Postcode), @Value(City), @Value(Country) addressdetails;1
    CONNECTION_TIMEOUT_LENGTH = 60
    ERROR_ATTR = _error
    FOLLOW_REDIRECTS = FOLLOW_WITH_GET
    HTTP_METHOD = GET
    REDIRECT_AUTH = ORIGINAL_DOMAIN_ONLY
    SAVE_FILE = Attribute
    STATUS_CODE_ATTR = _http_status_code
    TARGET_ATTR = _response_body
    TARGET_ATTR_ENCODING = auto-detect
    TARGET_URL = https://nominatim.openstreetmap.org/
    TRANSFER_TIMEOUT_LENGTH = 90
    USE_COOKIES = No
    VERIFY_SSL_CERTIFICATES = Yes
    -> AttributeManager
Note: Nettoyage des champs / _reponse_body => JSON_data / _http_status_code : delete
AttributeManager
    ATTR_TABLE:
      RENAME_SET_VALUE _response_body > JSON_data
      REMOVE _http_status_code
    -> JSONFragmenter
    -> JSONFragmenter_2
Note: JSONFragmenter / Le but est d'exploser un feature en plusieurs selon la valeur d'un attribut JSON. / L'attribut JSON doit être de type objet ou array pour que le transformer produise plusieurs fragments. / Dans notre cas, chaque réponse contient 0, 1 ou plusieurs objets, une adresse pouvant correspondre à plusieurs éléments (un batiment + une rue + un commerce...) / On sépare donc tous les objets de premier niveau de chaque feature : / json[*] / Voici un exemple d'objet récupéré (fragmenté) : / { / "place_id": 109530386, / "licence": "Data © OpenStreetMap contributors, ODbL 1.0. https://osm.org/copyright", / "osm_type": "way", / "osm_id": 83797499, / "boundingbox": [ / "46.1899015", / "46.1901095", / "6.3181443", / "6.3184118" / ], / "lat": "46.19000455", / "lon": "6.318287986430487", / "display_name": "90, Place de l'Église, Le Faubourg, Lucinges, Saint-Julien-en-Genevois, Haute-Savoie, Auvergne-Rhône-Alpes, France métropolitaine, 74380, France", / "class": "amenity", / "type": "townhall", / "importance": 0.7409999999999999, / "address": { / "house_number": "90", / "road": "Place de l'Église", / "isolated_dwelling": "Le Faubourg", / "village": "Lucinges", / "municipality": "Saint-Julien-en-Genevois", / "county": "Haute-Savoie", / "state": "Auvergne-Rhône-Alpes", / "country": "France", / "postcode": "74380", / "country_code": "fr" / } / }
JSONFragmenter
    EXPLODE_FORMAT = JSON
    EXTRACT_ATTR = No
    JSON_ATTR = JSON_data
    JSON_QUERY = json[*]
    READ_FROM_FILE = NO
    REJECT_EMPTY_LISTS = YES
    FRAGMENTS -> JSONExtractor
    FRAGMENTS -> JSONFlattener
Note: JSONExtractor / Le but est d'extraire les attributs JSON qui nous interessent dans des attributs FME. / Il est possible de concaténer des valeurs et d'ajouter des chaines de caractères : / + : concaténation / "ma chaine de texte" : ajout de caractères / Si l'attribut JSON est lui-même un objet, alors la valeur renvoyée sera au format JSON et pourra être extraite via un autre transformer du même type. / Pour extraire le code postale, on utilise la requête JSON suivante : / json["address"]["postcode"] / => json["address"] : on récupère la valeur de l'attribut "address" dans la valeur JSON / => ["postcode"] : on récupère la valeur de l'attribut "postcode" dans la valeur de l'attribut "address"
JSONExtractor
    EXTRACT_QUERY_TABLE = osm_id json["place_id"] latitude json["lat"] longitude json["lon"] classe json["class"] type json["type"] adresse_osm json["address"]["house_number"] + ", " + json["address"]["road"] + " " + json["address"]["postcode"] + " " + json["address"]["village"] adresse_osm_json json["address"]
    JSON_DOCUMENT = @Value(JSON_data)
    READ_FROM_FILE = NO
    EVALUATED -> AttributeManager_3
Note: Pour chaque adresse géocodée, il peut y avoir plusieurs résultats de géocodage. / On prend ici le premier qui arrive mais il est possible de pousser la détectition et de filtrer selon le type d'objet OpenStreetMap. / Chaque objet ayant une géométrie propre, le résultat peut être différent (vérifiez les résultats sur les communes ayant remontées plusieurs points) / Le transformer Geocoder ne récupère qu'une seule géométrie.
AttributeManager_3
    ATTR_TABLE:
      REMOVE JSON_data
      REMOVE json_type
      REMOVE json_index
      REMOVE type
      REMOVE classe
    -> VertexCreator
VertexCreator
    MEASURE_TYPE = Continuous
    MODE_NAME = Replace with Point
    XVAL = @Value(longitude)
    YVAL = @Value(latitude)
    -> CoordinateSystemSetter
CoordinateSystemSetter
    COORDSYS = EPSG:4326
    -> Sampler
Sampler
    GROUP_BY = id
    RATE = 1
    SAMPLE_MODE = No
    SAMPLE_TYPE_LONG = First N Features
Note: JSONFlattener / Le but du transformer est de récupérer tous les attributs JSON et de les placer dans des attributs FME. / Tous les attributs sont récupérés. Pour nos objets, les attributs d'adresse seront préfixé par l'attribut parent ("address") ce qui donnera par exemple adresse.postcode
JSONFlattener
    ERROR_LIST_ATTR = _json_error
    JSON_DOCUMENT = @Value(JSON_data)
    NEW_ATTRIBUTES = lat lon address.house_number address.road address.village address.city address.postcode address.country place_id class type
    READ_FROM_FILE = NO
    RECURSIVE = Yes
    -> AttributeManager_2
AttributeManager_2
    ATTR_TABLE:
      REMOVE JSON_data
      REMOVE json_type
      REMOVE json_index
      SET_TO adresse_osm = FME_CONDITIONAL:DEFAULT_VALUE'@Value(address.house_number), @Value(address.road) @Value(address.postcode) @Value(address.village) @Value(address.country)'BOOL_OP;OR;COMPOSITE_TEST;1;TEST address.city ATTRIBUTE_HAS_A_VALUE _FME_BLANK_STRING_'@Value(address.house_number), @Value(address.road) @Value(address.postcode) @Value(address.city) @Value(address.country)'FME_NUM_CONDITIONS2___
      REMOVE address.house_number
      REMOVE address.road
      REMOVE address.village
      REMOVE address.city
      REMOVE address.postcode
      REMOVE address.country
      REMOVE place_id
      REMOVE class
      REMOVE type
    -> VertexCreator_2
VertexCreator_2
    MEASURE_TYPE = Continuous
    MODE_NAME = Replace with Point
    XVAL = @Value(lat)
    YVAL = @Value(lon)
    -> CoordinateSystemSetter_2
CoordinateSystemSetter_2
    COORDSYS = EPSG:4326
    -> Sampler_2
Sampler_2
    GROUP_BY = id
    RATE = 1
    SAMPLE_MODE = No
    SAMPLE_TYPE_LONG = First N Features
Note: Même principe que le JSONFragmenter du dessus sauf qu'ici, on fragmente les features plusieurs fois : / json[*]["address"][*] / => json[*] : fragmentation entre chaque objet json de premier niveau (même nombre de fragment que le premier JSONFragmenter) / => ["addresse"] : fragmentation de chaque objet de premier niveau selon l'attribut "address" : il n'y en a qu'un seul donc pas de fragmentation supplémentaire. / => [*] : fragmentation de chaque objet "address" selon les attributs contenu dans l'objet "address" (un fragment par attribut présent) / Le nombre d'objet total est la multiplication du nombre de fragments produits à chaque étape de fragmentation. / La fragmenetation utilisé ici n'a pas d'intérêt et est juste présente pour l'exemple..
JSONFragmenter_2
    EXPLODE_FORMAT = JSON
    EXTRACT_ATTR = No
    JSON_ATTR = JSON_data
    JSON_QUERY = json[*]["address"][*]
    READ_FROM_FILE = NO
    REJECT_EMPTY_LISTS = YES
Geocoder
    GEOCODING_SERVICE = OpenStreetMap
    THREADS = 4
    TIMEOUT = 60
    -> AttributeManager_4
AttributeManager_4
    ATTR_TABLE:
      REMOVE _address_json
      REMOVE _address_types
      REMOVE _arcgis_wkid
      REMOVE _arcgis_longlabel
      REMOVE _arcgis_exinfo
      REMOVE _elevation_meters
      REMOVE _elevation_feet
      REMOVE _elevation_resolution
      REMOVE _postal_code
      REMOVE _tamu_census_block
      REMOVE _tamu_census_tract
      REMOVE _tamu_census_county_fips
      REMOVE _tamu_census_cbsa_fips
      REMOVE _tamu_census_mcd_fips
      REMOVE _tamu_census_place_fips
      REMOVE _tamu_census_state_fips
      REMOVE _tamu_census_year
      REMOVE _timezone
      REMOVE _timezone_name
      REMOVE _timezone_offset
      REMOVE _timezone_current_dst

FME workspace Tuto - Python.fmw
Title: Tuto - Python
Description: Ce script présente les possibilités offertes par Python dans FME
Plusieurs éléments (variable, fonction et import de module) sont créés dans le script au démarrage puis réutilisés dans les transformers et dans le script en fin
Plus d'information : https://blog.arthurbazin.com/programmation/gerez-le-python-qui-se-cache-dans-fme
Startup Python:
      # Import des modules FME
      import fme
      import fmeobjects

      # Création d'un logger pour afficher les messages
      global_logger = fmeobjects.FMELogFile()

      # Premier message
      global_logger.logMessageString(
      	''.ljust(100, '-') + '\n' +
      	'Startup Python Script '.ljust(100, '-') + '\n' +
      	''.ljust(100, '-'),
      	fmeobjects.FME_WARN
      )

      # Tout ce qui est défini ici sera disponible dans l'ensemble des scripts Python lors de l'execution du Workspace
      # Définition d'une variable
      global_var = "Startup Python Script"

      global_logger.logMessageString('	Variable globale : ' + global_var)

      # Définition d'une fonction
      def global_function(value):
      	return "Ma fonction globale retourne : " + value

      global_logger.logMessageString('	Résultat de fonction : ' + global_function('initialisation'))

      # Import d'un module
      import tuto_module


      global_logger.logMessageString('	Variable module : ' + tuto_module.module_var)

      global_logger.logMessageString('	Résultat fonction module : ' + tuto_module.module_function('initialisation'))


      global_logger.logMessageString(
      	''.ljust(100, '-') + '\n' +
      	'Startup Python Script '.ljust(100, '-') + '\n' +
      	''.ljust(100, '-'),
      	fmeobjects.FME_WARN
      )
Shutdown Python:
      # Pas besoin d'import des modules FME car ils ont été importés dans le script de démarrage

      # Premier message
      global_logger.logMessageString(
      	''.ljust(100, '-') + '\n' +
      	'Shutdown Python Script '.ljust(100, '-') + '\n' +
      	''.ljust(100, '-'),
      	fmeobjects.FME_WARN
      )

      # Tout ce qui a été défini est toujours présent
      # Variable
      global_logger.logMessageString('	Variable globale : ' + global_var)

      # Fonction

      global_logger.logMessageString('	Résultat de fonction : ' + global_function('shutdown'))

      # Module importé

      global_logger.logMessageString('	Variable module : ' + tuto_module.module_var)

      global_logger.logMessageString('	Résultat fonction module : ' + tuto_module.module_function('initialisation'))


      global_logger.logMessageString(
      	''.ljust(100, '-') + '\n' +
      	'Shutdown Python Script '.ljust(100, '-') + '\n' +
      	''.ljust(100, '-'),
      	fmeobjects.FME_WARN
      )

Note: Ce script présente les possibilités offertes par Python dans FME / Plusieurs éléments (variable, fonction et import de module) sont créés dans le script au démarrage puis réutilisés dans les transformers et dans le script en fin / Plus d'information : https://blog.arthurbazin.com/programmation/gerez-le-python-qui-se-cache-dans-fme
PythonCreator
    PYTHONSOURCE_NEW:
      # Import des modules FME non nécessaire car déjà fait dans le script au démarrage

      class FeatureCreator(object):

      	# Initialisation de la classe
      	def __init__(self):

      		# On réutilise des variables créées dans le script au démarrage

      		# Premier message
      		global_logger.logMessageString(
      			''.ljust(100, '-') + '\n' +
      			'PythonCreator '.ljust(100, '-') + '\n' +
      			''.ljust(100, '-'),
      			fmeobjects.FME_WARN
      		)

      		# Tout ce qui a été défini est toujours présent
      		# Variable
      		global_logger.logMessageString('	Variable globale : ' + global_var)

      		# Fonction

      		global_logger.logMessageString('	Résultat de fonction : ' + global_function('shutdown'))

      		# Module importé

      		global_logger.logMessageString('	Variable module : ' + tuto_module.module_var)

      		global_logger.logMessageString('	Résultat fonction module : ' + tuto_module.module_function('initialisation'))



      	# Méthode appelée (1 seule fois) pour créer l'objet initial
      	def input(self, feature):

      		# La variable "feature" issue du paramètre peut être mise de côté, elle ne sert qu'a FME et ne contient rien

      		# Création d'un objet
      		newFeature = fmeobjects.FMEFeature()

      		# Ajout d'attributs
      		newFeature.setAttribute(
      			"nom",
      			"Bazin"
      		)
      		newFeature.setAttribute(
      			"prenom",
      			"Arthur"
      		)

      		# Sortie de l'objet
      		self.pyoutput(newFeature)



      	# Fermeture de la classe
      	def close(self):

      		global_logger.logMessageString(
      			''.ljust(100, '-') + '\n' +
      			'PythonCreator '.ljust(100, '-') + '\n' +
      			''.ljust(100, '-'),
      			fmeobjects.FME_WARN
      		)
    PYTHONSYMBOL = FeatureCreator
    -> PythonCaller
PythonCaller [off]
    PYTHONSOURCE:
      # Import des modules FME non nécessaire car déjà fait dans le script au démarrage

      class FeatureProcessor(object):

      	# Initialisation de la classe
      	def __init__(self):

      		# On réutilise des variables créées dans le script au démarrage

      		# Premier message
      		global_logger.logMessageString(
      			''.ljust(100, '-') + '\n' +
      			'PythonCaller '.ljust(100, '-') + '\n' +
      			''.ljust(100, '-'),
      			fmeobjects.FME_WARN
      		)

      		# Tout ce qui a été défini est toujours présent
      		# Variable
      		global_logger.logMessageString('	Variable globale : ' + global_var)

      		# Fonction

      		global_logger.logMessageString('	Résultat de fonction : ' + global_function('shutdown'))

      		# Module importé

      		global_logger.logMessageString('	Variable module : ' + tuto_module.module_var)

      		global_logger.logMessageString('	Résultat fonction module : ' + tuto_module.module_function('initialisation'))



      	# Méthode appelée pour chaque objets (passé dans l'argument 'feature')
      	def input(self, feature):

      		# Affichage de la valeur du champ "nom" dans le log de FME
      		global_logger.logMessageString('Objet : ' + feature.getAttribute("nom"), fmeobjects.FME_INFORM)
      		# Ajout d'attributs
      		feature.setAttribute(
      			"sexe",
      			"Homme"
      		)
      		# Sortie de l'objet
      		self.pyoutput(feature)



      	# Fermeture de la classe
      	def close(self):

      		global_logger.logMessageString(
      			''.ljust(100, '-') + '\n' +
      			'PythonCaller '.ljust(100, '-') + '\n' +
      			''.ljust(100, '-'),
      			fmeobjects.FME_WARN
      		)
    PYTHONSYMBOL = FeatureProcessor

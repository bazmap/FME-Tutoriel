FME workspace Tuto - Transfert fichier.fmw
Title: Tuto - Transfert fichier
Description: Le but de ce workspace est de déplacer un fichier d'un stockage physique vers un autre.

Parameters:
- param_dest = $(FME_MF_DIR_USERTYPED)\media_export   # Emplacement des fichiers finaux
- SourceDataset_DATAFILE = $(FME_MF_DIR_USERTYPED)\media\*   # Source Data File(s)
- FEATURE_TYPES =

Readers:
- DATAFILE_2: DATAFILE from $(SourceDataset_DATAFILE)

Writers:
- DATAFILE_1: DATAFILE to $(param_dest)

Note: Le but de ce workspace est de déplacer un fichier d'un stockage physique vers un autre.
Note: Lecture de tous les fichiers du répertoire
DATAFILE (reader DATAFILE_2)
    -> File100 (writer DATAFILE_1)
Note: Ecriture dynamique de tous les éléments qui arrivent. / Attention, seul le nom est dynamique, les fichiers n'ont pas d'attributs a créer dynamiquement.
File100 (writer DATAFILE_1)

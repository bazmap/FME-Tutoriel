FME workspace raster_tiler.fmw

Parameters:
- source_data = C:\fmedata2019\Data\Orthophotos\*.tif   # Source de données 
- source_format = GEOTIFF
- source_SRID =   # Projection de la source de données
- dest_format = PNGRASTER   # PNG (Portable Network Graphics),PNGRASTER%JPEG (Joint Photographic Experts Group),JPEG Format de destination 
- dest_SRID = EPSG:3857   # 2154 - Lambert93,EPSG:2154%3857 - Spherical Mercator,EPSG:3857 Projection de destination 
- dest_data = C:\tmp   # Emplacement des fichiers de destination
- param_nbr_niveau = 5   # Nombre de niveaux 
- param_cell_size = 638.206150234415   # Taille de cellule (pixel) en mètre
- param_tile_size = 256   # Dimension des tuiles (en pixel) 

Readers:
- GENERIC_1: GENERIC from $(source_data) in $(source_SRID)

Writers:
- GENERIC_2: GENERIC to $(dest_data) in $(dest_SRID)

GEOTIFF (reader GENERIC_1)
    -> RasterMosaicker
RasterMosaicker
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Resample
    -> Cloner
Cloner
    COPIES = $(param_nbr_niveau)
    COPYATT = niveau_z
    COPY -> AttributeManager_12
AttributeManager_12
    ATTR_TABLE = SET_TO taille_cellule = @Evaluate($(param_cell_size)/pow(2,@Value(niveau_z)))
    -> RasterResampler_12
RasterResampler_12
    INTERPOLATION_TYPE_NAME = Nearest Neighbor
    ROWCOL_OR_CELLSIZE = CellSize
    X_CELL_SIZE = @Value(taille_cellule)
    Y_CELL_SIZE = @Value(taille_cellule)
    RESAMPLED -> RasterTiler_13
RasterTiler_13
    FORCE_EQUAL_SIZED_TILES = No
    NUM_TILE_COLUMNS = $(param_tile_size)
    NUM_TILE_ROWS = $(param_tile_size)
    SEED_COLUMN = 0
    SEED_ROW = 0
    TILESIZE_OR_NUMTILES = Tile Size
    TILE_COLUMN_ATTRIBUTE = niveau_y
    TILE_ROW_ATTRIBUTE = niveau_x
    TILES -> _num_tile_column (writer GENERIC_2)
_num_tile_column (writer GENERIC_2)
    attributes: niveau_z varchar(200), taille_cellule varchar(200), niveau_y varchar(200), niveau_x varchar(200)
RasterRGBCreator
    BAND_COLOR_MODEL = RGB24
    CREATE_PALETTE = No
    MAX_COLOR_VALUE = 1,1,1
    MIN_COLOR_VALUE = 0,0,0
    RASTER_TYPE_PARAM = Single Value
    ROTATION = 0.0
    ROWCOL_OR_CELLSIZE = Extents
    X_CELL_ORIGIN = 0.5
    X_LOWER_RIGHT_COORD = 0.0
    X_SPACING = 1.0
    X_UPPER_LEFT_COORD = 0.0
    Y_CELL_ORIGIN = 0.5
    Y_LOWER_RIGHT_COORD = 0.0
    Y_SPACING = 1.0
    Y_UPPER_LEFT_COORD = 0.0
RasterNumericCreator
    CELL_ELEMENT_TYPE = UInt32
    MAX_NUMERIC_VALUE = 0
    MIN_NUMERIC_VALUE = 0
    RASTER_TYPE_PARAM = Single Value
    ROTATION = 0.0
    ROWCOL_OR_CELLSIZE = RowsColumns
    X_CELL_ORIGIN = 0.5
    X_LOWER_RIGHT_COORD = 0.0
    X_SPACING = 1.0
    X_UPPER_LEFT_COORD = 0.0
    Y_CELL_ORIGIN = 0.5
    Y_LOWER_RIGHT_COORD = 0.0
    Y_SPACING = 1.0
    Y_UPPER_LEFT_COORD = 0.0
